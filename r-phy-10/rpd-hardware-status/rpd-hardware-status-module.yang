module rpd-hardware-status-module {
    yang-version 1;
    /* This file is automatically generated with Falcon V System's script.
       Any change made to this file will be lost. */

    namespace "falconvsystems:r-phy-10:rpd-hardware-status-module";
    prefix "p-rpd-hardware-status";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-RpdHardwareStatus {
        tlv:id 130;
        description "TLV [130]: RpdHardwareStatus";
        leaf RpdCpuTemperature {
            tlv:id 1;
            type uint8;
            description "TLV [130.1]: RpdHardwareStatus.RpdCpuTemperature";
        }

        leaf RpdMotherboardTemperature {
            tlv:id 2;
            type uint8;
            description "TLV [130.2]: RpdHardwareStatus.RpdMotherboardTemperature";
        }

    }  // g-RpdHardwareStatus grouping

}
