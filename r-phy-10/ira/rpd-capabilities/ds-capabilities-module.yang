module ds-capabilities-module {
    yang-version 1;
    /* This file is automatically generated with Falcon V System's script.
       Any change made to this file will be lost. */

    namespace "falconvsystems:r-phy-10:ds-capabilities-module";
    prefix "p-ds-capabilities";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-DsCapabilities {
        tlv:id 51;
        description
            "TLV [50.51]: RpdCapabilities.DsCapabilities
             non-defaults: [is_rcp_readonly: True, is_readonly: True]";

        leaf DsScqamInterleverSupport {
            tlv:id 1;
            type uint32;
            description
                "TLV [50.51.1]: RpdCapabilities.DsCapabilities.DsScqamInterleverSupport
                 non-defaults: [is_rcp_readonly: True, is_readonly: True]";
        }

        leaf DsMaxDocsisScQamChannels {
            tlv:id 2;
            type uint16;
            description
                "TLV [50.51.2]: RpdCapabilities.DsCapabilities.DsMaxDocsisScQamChannels
                 non-defaults: [is_rcp_readonly: True, is_readonly: True]";
        }

        leaf DsMaxMultipleScQamPspSessions {
            tlv:id 3;
            type uint16;
            description
                "TLV [50.51.3]: RpdCapabilities.DsCapabilities.DsMaxMultipleScQamPspSessions
                 non-defaults: [is_rcp_readonly: True, is_readonly: True]";
        }

    }  // g-DsCapabilities grouping

}
