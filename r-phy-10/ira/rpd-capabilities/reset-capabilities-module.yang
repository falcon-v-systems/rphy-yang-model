module reset-capabilities-module {
    yang-version 1;
    /* This file is automatically generated with Falcon V System's script.
       Any change made to this file will be lost. */

    namespace "falconvsystems:r-phy-10:reset-capabilities-module";
    prefix "p-reset-capabilities";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-ResetCapabilities {
        tlv:id 55;
        description
            "TLV [50.55]: RpdCapabilities.ResetCapabilities
             non-defaults: [is_rcp_readonly: True, is_readonly: True]";

        leaf SoftResetSupported {
            tlv:id 1;
            type boolean;
            description
                "TLV [50.55.1]: RpdCapabilities.ResetCapabilities.SoftResetSupported
                 non-defaults: [is_rcp_readonly: True, is_readonly: True]";
        }

        leaf NvResetSupported {
            tlv:id 2;
            type boolean;
            description
                "TLV [50.55.2]: RpdCapabilities.ResetCapabilities.NvResetSupported
                 non-defaults: [is_rcp_readonly: True, is_readonly: True]";
        }

        leaf FactoryResetSupported {
            tlv:id 3;
            type boolean;
            description
                "TLV [50.55.3]: RpdCapabilities.ResetCapabilities.FactoryResetSupported
                 non-defaults: [is_rcp_readonly: True, is_readonly: True]";
        }

    }  // g-ResetCapabilities grouping

}
