module lcce-channel-reachability-module {
    yang-version 1;
    /* This file is automatically generated with Falcon V System's script.
       Any change made to this file will be lost. */

    namespace "falconvsystems:r-phy-10:lcce-channel-reachability-module";
    prefix "p-lcce-channel-reachability";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-LcceChannelReachability {
        tlv:id 20;
        description
            "TLV [50.20]: RpdCapabilities.LcceChannelReachability
             non-defaults: [is_rcp_readonly: True, is_readonly: True]";

        leaf EnetPortIndex {
            tlv:id 1;
            type uint8;
            description
                "TLV [50.20.1]: RpdCapabilities.LcceChannelReachability.EnetPortIndex
                 non-defaults: [is_key: True, is_rcp_readonly: True, is_readonly: True]";
        }

        leaf ChannelType {
            tlv:id 2;
            tlv:repr uint8;
            type enumeration {
                enum DsScQam    { value  1; description ""; }
                enum DsOfdm     { value  2; description ""; }
                enum Ndf        { value  3; description ""; }
                enum DsScte55d1 { value  4; description ""; }
                enum UsAtdma    { value  5; description ""; }
                enum UsOfdma    { value  6; description ""; }
                enum reserved   { value  7; description ""; }
                enum Ndr        { value  8; description ""; }
                enum UsScte55d1 { value  9; description ""; }
            }
            description
                "TLV [50.20.2]: RpdCapabilities.LcceChannelReachability.ChannelType
                 non-defaults: [is_key: True, is_rcp_readonly: True, is_readonly: True]";
        }

        leaf RfPortIndex {
            tlv:id 3;
            type uint8;
            description
                "TLV [50.20.3]: RpdCapabilities.LcceChannelReachability.RfPortIndex
                 non-defaults: [is_key: True, is_rcp_readonly: True, is_readonly: True]";
        }

        leaf StartChannelIndex {
            tlv:id 4;
            type uint8;
            description
                "TLV [50.20.4]: RpdCapabilities.LcceChannelReachability.StartChannelIndex
                 non-defaults: [is_rcp_readonly: True, is_readonly: True]";
        }

        leaf EndChannelIndex {
            tlv:id 5;
            type uint8;
            description
                "TLV [50.20.5]: RpdCapabilities.LcceChannelReachability.EndChannelIndex
                 non-defaults: [is_rcp_readonly: True, is_readonly: True]";
        }

    }  // g-LcceChannelReachability grouping

}
