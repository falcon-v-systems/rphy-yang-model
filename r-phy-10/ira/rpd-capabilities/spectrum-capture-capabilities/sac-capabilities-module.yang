module sac-capabilities-module {
    yang-version 1;
    /* This file is automatically generated with Falcon V System's script.
       Any change made to this file will be lost. */

    namespace "falconvsystems:r-phy-10:sac-capabilities-module";
    prefix "p-sac-capabilities";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-SacCapabilities {
        tlv:id 2;
        description
            "TLV [50.59.2]: RpdCapabilities.SpectrumCaptureCapabilities.SacCapabilities
             non-defaults: [is_rcp_readonly: True, is_readonly: True]";

        leaf SacIndex {
            tlv:id 1;
            type uint8;
            description
                "TLV [50.59.2.1]: RpdCapabilities.SpectrumCaptureCapabilities.SacCapabilities.SacIndex
                 non-defaults: [is_rcp_readonly: True, is_readonly: True]";
        }

        leaf SacDescription {
            tlv:id 2;
            type string;
            description
                "TLV [50.59.2.2]: RpdCapabilities.SpectrumCaptureCapabilities.SacCapabilities.SacDescription
                 non-defaults: [is_rcp_readonly: True, is_readonly: True]";
        }

        leaf MaxCaptureSpan {
            tlv:id 3;
            type uint32;
            units "Hz";
            description
                "TLV [50.59.2.3]: RpdCapabilities.SpectrumCaptureCapabilities.SacCapabilities.MaxCaptureSpan
                 non-defaults: [is_rcp_readonly: True, is_readonly: True]";
        }

        leaf MinimumCaptureFrequency {
            tlv:id 4;
            type uint32;
            units "Hz";
            description
                "TLV [50.59.2.4]: RpdCapabilities.SpectrumCaptureCapabilities.SacCapabilities.MinimumCaptureFrequency
                 non-defaults: [is_rcp_readonly: True, is_readonly: True]";
        }

        leaf MaximumCaptureFrequency {
            tlv:id 5;
            type uint32;
            units "Hz";
            description
                "TLV [50.59.2.5]: RpdCapabilities.SpectrumCaptureCapabilities.SacCapabilities.MaximumCaptureFrequency
                 non-defaults: [is_rcp_readonly: True, is_readonly: True]";
        }

        leaf SupportedTriggerModes {
            tlv:id 6;
            type uint32;
            description
                "TLV [50.59.2.6]: RpdCapabilities.SpectrumCaptureCapabilities.SacCapabilities.SupportedTriggerModes
                 non-defaults: [is_rcp_readonly: True, is_readonly: True]";
        }

        leaf SupportedOutputFormats {
            tlv:id 7;
            type uint32;
            description
                "TLV [50.59.2.7]: RpdCapabilities.SpectrumCaptureCapabilities.SacCapabilities.SupportedOutputFormats
                 non-defaults: [is_rcp_readonly: True, is_readonly: True]";
        }

        leaf SupportedWindowFormats {
            tlv:id 8;
            type uint32;
            description
                "TLV [50.59.2.8]: RpdCapabilities.SpectrumCaptureCapabilities.SacCapabilities.SupportedWindowFormats
                 non-defaults: [is_rcp_readonly: True, is_readonly: True]";
        }

        leaf SupportsAveraging {
            tlv:id 9;
            type boolean;
            description
                "TLV [50.59.2.9]: RpdCapabilities.SpectrumCaptureCapabilities.SacCapabilities.SupportsAveraging
                 non-defaults: [is_rcp_readonly: True, is_readonly: True]";
        }

        leaf SupportedAggregationMethods {
            tlv:id 10;
            type uint32;
            description
                "TLV [50.59.2.10]: RpdCapabilities.SpectrumCaptureCapabilities.SacCapabilities.SupportedAggregationMethods
                 non-defaults: [is_rcp_readonly: True, is_readonly: True]";
        }

        leaf SupportsSpectrumQualification {
            tlv:id 11;
            type boolean;
            description
                "TLV [50.59.2.11]: RpdCapabilities.SpectrumCaptureCapabilities.SacCapabilities.SupportsSpectrumQualification
                 non-defaults: [is_rcp_readonly: True, is_readonly: True]";
        }

        leaf MaxNumBins {
            tlv:id 12;
            type uint16;
            description
                "TLV [50.59.2.12]: RpdCapabilities.SpectrumCaptureCapabilities.SacCapabilities.MaxNumBins
                 non-defaults: [is_rcp_readonly: True, is_readonly: True]";
        }

        leaf MinNumBins {
            tlv:id 13;
            type uint16;
            description
                "TLV [50.59.2.13]: RpdCapabilities.SpectrumCaptureCapabilities.SacCapabilities.MinNumBins
                 non-defaults: [is_rcp_readonly: True, is_readonly: True]";
        }

        leaf MinRepeatPeriod {
            tlv:id 14;
            type uint32;
            units "microseconds";
            description
                "TLV [50.59.2.14]: RpdCapabilities.SpectrumCaptureCapabilities.SacCapabilities.MinRepeatPeriod
                 non-defaults: [is_rcp_readonly: True, is_readonly: True]";
        }

        leaf SupportedTrigChanTypes {
            tlv:id 15;
            type uint8;
            description
                "TLV [50.59.2.15]: RpdCapabilities.SpectrumCaptureCapabilities.SacCapabilities.SupportedTrigChanTypes
                 non-defaults: [is_rcp_readonly: True, is_readonly: True]";
        }

        leaf PwType {
            tlv:id 16;
            tlv:repr uint8;
            type enumeration {
                enum PNM_PW     { value  0; description ""; }
                enum SpecMan_PW { value  1; description ""; }
            }
            description
                "TLV [50.59.2.16]: RpdCapabilities.SpectrumCaptureCapabilities.SacCapabilities.PwType
                 non-defaults: [is_rcp_readonly: True, is_readonly: True]";
        }

        leaf LowestCapturePort {
            tlv:id 17;
            type uint8;
            description
                "TLV [50.59.2.17]: RpdCapabilities.SpectrumCaptureCapabilities.SacCapabilities.LowestCapturePort
                 non-defaults: [is_rcp_readonly: True, is_readonly: True]";
        }

        leaf HighestCapturePort {
            tlv:id 18;
            type uint8;
            description
                "TLV [50.59.2.18]: RpdCapabilities.SpectrumCaptureCapabilities.SacCapabilities.HighestCapturePort
                 non-defaults: [is_rcp_readonly: True, is_readonly: True]";
        }

        leaf SupportsScanningCapture {
            tlv:id 19;
            type boolean;
            description
                "TLV [50.59.2.19]: RpdCapabilities.SpectrumCaptureCapabilities.SacCapabilities.SupportsScanningCapture
                 non-defaults: [is_rcp_readonly: True, is_readonly: True]";
        }

        leaf MinScanningRepeatPeriod {
            tlv:id 20;
            type uint32;
            units "microseconds";
            description
                "TLV [50.59.2.20]: RpdCapabilities.SpectrumCaptureCapabilities.SacCapabilities.MinScanningRepeatPeriod
                 non-defaults: [is_rcp_readonly: True, is_readonly: True]";
        }

    }  // g-SacCapabilities grouping

}
