module spectrum-capture-capabilities-module {
    yang-version 1;
    /* This file is automatically generated with Falcon V System's script.
       Any change made to this file will be lost. */

    namespace "falconvsystems:r-phy-10:spectrum-capture-capabilities-module";
    prefix "p-spectrum-capture-capabilities";

    // --- imports ---------------------------------------

    import sac-capabilities-module {
        prefix "p-sac-capabilities";
        /*  File path: ira/rpd-capabilities/spectrum-capture-capabilities/sac-capabilities-module.yang
            https://github.com/falcon-v-systems/rphy-yang-model/blob/master/r-phy-10/ira/rpd-capabilities/spectrum-capture-capabilities/sac-capabilities-module.yang */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-SpectrumCaptureCapabilities {
        tlv:id 59;
        description
            "TLV [50.59]: RpdCapabilities.SpectrumCaptureCapabilities
             non-defaults: [is_rcp_readonly: True, is_readonly: True]";

        leaf NumSacs {
            tlv:id 1;
            type uint8;
            description
                "TLV [50.59.1]: RpdCapabilities.SpectrumCaptureCapabilities.NumSacs
                 non-defaults: [is_rcp_readonly: True, is_readonly: True]";
        }

        container SacCapabilities {
            tlv:id 2;
            description
                "TLV [50.59.2]: RpdCapabilities.SpectrumCaptureCapabilities.SacCapabilities
                 non-defaults: [is_rcp_readonly: True, is_readonly: True]";
            uses "p-sac-capabilities:g-SacCapabilities";
        }

    }  // g-SpectrumCaptureCapabilities grouping

}
