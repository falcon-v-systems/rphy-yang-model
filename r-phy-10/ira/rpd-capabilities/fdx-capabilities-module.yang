module fdx-capabilities-module {
    yang-version 1;
    /* This file is automatically generated with Falcon V System's script.
       Any change made to this file will be lost. */

    namespace "falconvsystems:r-phy-10:fdx-capabilities-module";
    prefix "p-fdx-capabilities";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-FdxCapabilities {
        tlv:id 57;
        description
            "TLV [50.57]: RpdCapabilities.FdxCapabilities
             non-defaults: [is_rcp_readonly: True, is_readonly: True]";

        leaf SupportFdx {
            tlv:id 1;
            type boolean;
            description
                "TLV [50.57.1]: RpdCapabilities.FdxCapabilities.SupportFdx
                 non-defaults: [is_rcp_readonly: True, is_readonly: True]";
        }

        leaf SupportZblInsertion {
            tlv:id 2;
            type boolean;
            description
                "TLV [50.57.2]: RpdCapabilities.FdxCapabilities.SupportZblInsertion
                 non-defaults: [is_rcp_readonly: True, is_readonly: True]";
        }

        leaf ZblInsMsgLeadTime {
            tlv:id 3;
            type uint16;
            units "microseconds";
            description
                "TLV [50.57.3]: RpdCapabilities.FdxCapabilities.ZblInsMsgLeadTime
                 non-defaults: [is_rcp_readonly: True, is_readonly: True]";
        }

    }  // g-FdxCapabilities grouping

}
