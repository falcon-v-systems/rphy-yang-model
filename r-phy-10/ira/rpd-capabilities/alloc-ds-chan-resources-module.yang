module alloc-ds-chan-resources-module {
    yang-version 1;
    /* This file is automatically generated with Falcon V System's script.
       Any change made to this file will be lost. */

    namespace "falconvsystems:r-phy-10:alloc-ds-chan-resources-module";
    prefix "p-alloc-ds-chan-resources";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-AllocDsChanResources {
        tlv:id 22;
        description
            "TLV [50.22]: RpdCapabilities.AllocDsChanResources
             non-defaults: [is_rcp_readonly: True, is_readonly: True]";

        leaf DsPortIndex {
            tlv:id 1;
            type uint8;
            description
                "TLV [50.22.1]: RpdCapabilities.AllocDsChanResources.DsPortIndex
                 non-defaults: [is_key: True, is_rcp_readonly: True, is_readonly: True]";
        }

        leaf AllocatedDsOfdmChannels {
            tlv:id 2;
            type uint16;
            description
                "TLV [50.22.2]: RpdCapabilities.AllocDsChanResources.AllocatedDsOfdmChannels
                 non-defaults: [is_rcp_readonly: True, is_readonly: True]";
        }

        leaf AllocatedDsScQamChannels {
            tlv:id 3;
            type uint16;
            description
                "TLV [50.22.3]: RpdCapabilities.AllocDsChanResources.AllocatedDsScQamChannels
                 non-defaults: [is_rcp_readonly: True, is_readonly: True]";
        }

        leaf AllocatedDsOob55d1Channels {
            tlv:id 4;
            type uint16;
            description
                "TLV [50.22.4]: RpdCapabilities.AllocDsChanResources.AllocatedDsOob55d1Channels
                 non-defaults: [is_rcp_readonly: True, is_readonly: True]";
        }

        leaf Deprecated {
            tlv:id 5;
            type uint16;
            description
                "TLV [50.22.5]: RpdCapabilities.AllocDsChanResources.Deprecated
                 non-defaults: [is_rcp_readonly: True, is_readonly: True]";
        }

        leaf AllocatedNdfChannels {
            tlv:id 6;
            type uint16;
            description
                "TLV [50.22.6]: RpdCapabilities.AllocDsChanResources.AllocatedNdfChannels
                 non-defaults: [is_rcp_readonly: True, is_readonly: True]";
        }

    }  // g-AllocDsChanResources grouping

}
