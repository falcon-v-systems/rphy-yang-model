module alloc-us-chan-resources-module {
    yang-version 1;
    /* This file is automatically generated with Falcon V System's script.
       Any change made to this file will be lost. */

    namespace "falconvsystems:r-phy-10:alloc-us-chan-resources-module";
    prefix "p-alloc-us-chan-resources";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-AllocUsChanResources {
        tlv:id 23;
        description
            "TLV [50.23]: RpdCapabilities.AllocUsChanResources
             non-defaults: [is_rcp_readonly: True, is_readonly: True]";

        leaf UsPortIndex {
            tlv:id 1;
            type uint8;
            description
                "TLV [50.23.1]: RpdCapabilities.AllocUsChanResources.UsPortIndex
                 non-defaults: [is_key: True, is_rcp_readonly: True, is_readonly: True]";
        }

        leaf AllocatedUsOfdmaChannels {
            tlv:id 2;
            type uint16;
            description
                "TLV [50.23.2]: RpdCapabilities.AllocUsChanResources.AllocatedUsOfdmaChannels
                 non-defaults: [is_rcp_readonly: True, is_readonly: True]";
        }

        leaf AllocatedUsScQamChannels {
            tlv:id 3;
            type uint16;
            description
                "TLV [50.23.3]: RpdCapabilities.AllocUsChanResources.AllocatedUsScQamChannels
                 non-defaults: [is_rcp_readonly: True, is_readonly: True]";
        }

        leaf AllocatedUsOob55d1Channels {
            tlv:id 4;
            type uint16;
            description
                "TLV [50.23.4]: RpdCapabilities.AllocUsChanResources.AllocatedUsOob55d1Channels
                 non-defaults: [is_rcp_readonly: True, is_readonly: True]";
        }

        leaf Deprecated {
            tlv:id 5;
            type uint16;
            description
                "TLV [50.23.5]: RpdCapabilities.AllocUsChanResources.Deprecated
                 non-defaults: [is_rcp_readonly: True, is_readonly: True]";
        }

        leaf AllocatedNdrChannels {
            tlv:id 6;
            type uint16;
            description
                "TLV [50.23.6]: RpdCapabilities.AllocUsChanResources.AllocatedNdrChannels
                 non-defaults: [is_rcp_readonly: True, is_readonly: True]";
        }

    }  // g-AllocUsChanResources grouping

}
