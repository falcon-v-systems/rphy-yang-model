module gcp-capabilities-module {
    yang-version 1;
    /* This file is automatically generated with Falcon V System's script.
       Any change made to this file will be lost. */

    namespace "falconvsystems:r-phy-10:gcp-capabilities-module";
    prefix "p-gcp-capabilities";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-GcpCapabilities {
        tlv:id 52;
        description
            "TLV [50.52]: RpdCapabilities.GcpCapabilities
             non-defaults: [is_rcp_readonly: True, is_readonly: True]";

        leaf GcpKaResponseTime {
            tlv:id 1;
            type uint16;
            units "miliseconds";
            description
                "TLV [50.52.1]: RpdCapabilities.GcpCapabilities.GcpKaResponseTime
                 non-defaults: [is_rcp_readonly: True, is_readonly: True]";
        }

    }  // g-GcpCapabilities grouping

}
