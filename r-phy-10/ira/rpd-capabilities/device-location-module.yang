module device-location-module {
    yang-version 1;
    /* This file is automatically generated with Falcon V System's script.
       Any change made to this file will be lost. */

    namespace "falconvsystems:r-phy-10:device-location-module";
    prefix "p-device-location";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-DeviceLocation {
        tlv:id 24;
        description
            "TLV [50.24]: RpdCapabilities.DeviceLocation
             non-defaults: [is_rcp_readonly: True, is_readonly: True]";

        leaf DeviceLocationDescription {
            tlv:id 1;
            type string;
            description
                "TLV [50.24.1]: RpdCapabilities.DeviceLocation.DeviceLocationDescription";
        }

        leaf GeoLocationLatitude {
            tlv:id 2;
            type string;
            description
                "TLV [50.24.2]: RpdCapabilities.DeviceLocation.GeoLocationLatitude";
        }

        leaf GeoLocationLongitude {
            tlv:id 3;
            type string;
            description
                "TLV [50.24.3]: RpdCapabilities.DeviceLocation.GeoLocationLongitude";
        }

    }  // g-DeviceLocation grouping

}
