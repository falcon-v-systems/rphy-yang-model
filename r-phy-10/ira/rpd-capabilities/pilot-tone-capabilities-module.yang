module pilot-tone-capabilities-module {
    yang-version 1;
    /* This file is automatically generated with Falcon V System's script.
       Any change made to this file will be lost. */

    namespace "falconvsystems:r-phy-10:pilot-tone-capabilities-module";
    prefix "p-pilot-tone-capabilities";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-PilotToneCapabilities {
        tlv:id 21;
        description
            "TLV [50.21]: RpdCapabilities.PilotToneCapabilities
             non-defaults: [is_rcp_readonly: True, is_readonly: True]";

        leaf NumCwToneGens {
            tlv:id 1;
            type uint8;
            description
                "TLV [50.21.1]: RpdCapabilities.PilotToneCapabilities.NumCwToneGens
                 non-defaults: [is_rcp_readonly: True, is_readonly: True]";
        }

        leaf LowestCwToneFreq {
            tlv:id 2;
            type uint32;
            description
                "TLV [50.21.2]: RpdCapabilities.PilotToneCapabilities.LowestCwToneFreq
                 non-defaults: [is_rcp_readonly: True, is_readonly: True]";
        }

        leaf HighestCwToneFreq {
            tlv:id 3;
            type uint32;
            description
                "TLV [50.21.3]: RpdCapabilities.PilotToneCapabilities.HighestCwToneFreq
                 non-defaults: [is_rcp_readonly: True, is_readonly: True]";
        }

        leaf MaxPowerDedCwTone {
            tlv:id 4;
            type uint16;
            units "TenthdB";
            description
                "TLV [50.21.4]: RpdCapabilities.PilotToneCapabilities.MaxPowerDedCwTone
                 non-defaults: [is_rcp_readonly: True, is_readonly: True]";
        }

        leaf QamAsPilot {
            tlv:id 5;
            type boolean;
            description
                "TLV [50.21.5]: RpdCapabilities.PilotToneCapabilities.QamAsPilot
                 non-defaults: [is_rcp_readonly: True, is_readonly: True]";
        }

        leaf MinPowerDedCwTone {
            tlv:id 6;
            type int16;
            units "TenthdB";
            description
                "TLV [50.21.6]: RpdCapabilities.PilotToneCapabilities.MinPowerDedCwTone
                 non-defaults: [is_rcp_readonly: True, is_readonly: True]";
        }

        leaf MaxPowerQamCwTone {
            tlv:id 7;
            type uint16;
            units "TenthdB";
            description
                "TLV [50.21.7]: RpdCapabilities.PilotToneCapabilities.MaxPowerQamCwTone
                 non-defaults: [is_rcp_readonly: True, is_readonly: True]";
        }

        leaf MinPowerQamCwTone {
            tlv:id 8;
            type int16;
            units "TenthdB";
            description
                "TLV [50.21.8]: RpdCapabilities.PilotToneCapabilities.MinPowerQamCwTone
                 non-defaults: [is_rcp_readonly: True, is_readonly: True]";
        }

    }  // g-PilotToneCapabilities grouping

}
