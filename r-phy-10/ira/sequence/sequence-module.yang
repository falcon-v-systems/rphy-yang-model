module sequence-module {
    yang-version 1;
    /* This file is automatically generated with Falcon V System's script.
       Any change made to this file will be lost. */

    namespace "falconvsystems:r-phy-10:sequence-module";
    prefix "p-sequence";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping Sequence-grouping {
        tlv:id 9;
        description
            "Attribute of `Object` type.
             TLV [9]: Sequence";

        leaf SequenceNumber {
            tlv:id 10;
            type uint16;
            description
                "TLV [10]: SequenceNumber";
        }

    }  // Sequence-grouping

}
