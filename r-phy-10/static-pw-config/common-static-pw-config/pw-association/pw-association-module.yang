module pw-association-module {
    yang-version 1;
    /* This file is automatically generated with Falcon V System's script.
       Any change made to this file will be lost. */

    namespace "falconvsystems:r-phy-10:pw-association-module";
    prefix "p-pw-association";

    // --- imports ---------------------------------------

    import channel-selector-module {
        prefix "p-channel-selector";
        description 
            "File path: static-pw-config/common-static-pw-config/pw-association/channel-selector-module.yang
            https://github.com/falcon-v-systems/rphy-yang-model/blob/master/r-phy-10/static-pw-config/common-static-pw-config/pw-association/channel-selector-module.yang";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-PwAssociation {
        tlv:id 11;
        description
            "TLV [58.3.11]: StaticPwConfig.CommonStaticPwConfig.PwAssociation";
        leaf Index {
            tlv:id 1;
            type uint8;
            description
                "TLV [58.3.11.1]: StaticPwConfig.CommonStaticPwConfig.PwAssociation.Index
                 non-defaults: [is_key: True]";
        }

        container ChannelSelector {
            tlv:id 2;
            description
                "TLV [58.3.11.2]: StaticPwConfig.CommonStaticPwConfig.PwAssociation.ChannelSelector";
            uses "p-channel-selector:g-ChannelSelector";
        }

    }  // g-PwAssociation grouping

}
