module main-rcp_tlv_def-module {
    yang-version 1;
    /* This file is automatically generated with Falcon V System's script.
       Any change made to this file will be lost. */

    namespace "falconvsystems:r-phy-10:main-rcp_tlv_def-module";
    prefix "p-main-rcp_tlv_def";

    // --- imports ---------------------------------------

    import ccap-core-identification-module {
        prefix "p-ccap-core-identification";
        description 
            "File path: ccap-core-identification/ccap-core-identification-module.yang
            https://github.com/falcon-v-systems/rphy-yang-model/blob/master/r-phy-10/ccap-core-identification/ccap-core-identification-module.yang";
    }

    import core-gcp-connection-response-module {
        prefix "p-core-gcp-connection-response";
        description 
            "File path: core-gcp-connection-response/core-gcp-connection-response-module.yang
            https://github.com/falcon-v-systems/rphy-yang-model/blob/master/r-phy-10/core-gcp-connection-response/core-gcp-connection-response-module.yang";
    }

    import docs-if-module {
        prefix "p-docs-if";
        description 
            "File path: docs-if/docs-if-module.yang
            https://github.com/falcon-v-systems/rphy-yang-model/blob/master/r-phy-10/docs-if/docs-if-module.yang";
    }

    import docs-if3-module {
        prefix "p-docs-if3";
        description 
            "File path: docs-if3/docs-if3-module.yang
            https://github.com/falcon-v-systems/rphy-yang-model/blob/master/r-phy-10/docs-if3/docs-if3-module.yang";
    }

    import docs-if31-module {
        prefix "p-docs-if31";
        description 
            "File path: docs-if31/docs-if31-module.yang
            https://github.com/falcon-v-systems/rphy-yang-model/blob/master/r-phy-10/docs-if31/docs-if31-module.yang";
    }

    import ds-ofdm-channel-config-module {
        prefix "p-ds-ofdm-channel-config";
        description 
            "File path: ds-ofdm-channel-config/ds-ofdm-channel-config-module.yang
            https://github.com/falcon-v-systems/rphy-yang-model/blob/master/r-phy-10/ds-ofdm-channel-config/ds-ofdm-channel-config-module.yang";
    }

    import ds-ofdm-channel-perf-module {
        prefix "p-ds-ofdm-channel-perf";
        description 
            "File path: ds-ofdm-channel-perf/ds-ofdm-channel-perf-module.yang
            https://github.com/falcon-v-systems/rphy-yang-model/blob/master/r-phy-10/ds-ofdm-channel-perf/ds-ofdm-channel-perf-module.yang";
    }

    import ds-ofdm-profile-module {
        prefix "p-ds-ofdm-profile";
        description 
            "File path: ds-ofdm-profile/ds-ofdm-profile-module.yang
            https://github.com/falcon-v-systems/rphy-yang-model/blob/master/r-phy-10/ds-ofdm-profile/ds-ofdm-profile-module.yang";
    }

    import ds-oob551l-perf-module {
        prefix "p-ds-oob551l-perf";
        description 
            "File path: ds-oob551l-perf/ds-oob551l-perf-module.yang
            https://github.com/falcon-v-systems/rphy-yang-model/blob/master/r-phy-10/ds-oob551l-perf/ds-oob551l-perf-module.yang";
    }

    import ds-oob552-perf-module {
        prefix "p-ds-oob552-perf";
        description 
            "File path: ds-oob552-perf/ds-oob552-perf-module.yang
            https://github.com/falcon-v-systems/rphy-yang-model/blob/master/r-phy-10/ds-oob552-perf/ds-oob552-perf-module.yang";
    }

    import ds-oob55d1-module {
        prefix "p-ds-oob55d1";
        description 
            "File path: ds-oob55d1/ds-oob55d1-module.yang
            https://github.com/falcon-v-systems/rphy-yang-model/blob/master/r-phy-10/ds-oob55d1/ds-oob55d1-module.yang";
    }

    import ds-rf-port-module {
        prefix "p-ds-rf-port";
        description 
            "File path: ds-rf-port/ds-rf-port-module.yang
            https://github.com/falcon-v-systems/rphy-yang-model/blob/master/r-phy-10/ds-rf-port/ds-rf-port-module.yang";
    }

    import ds-rf-port-perf-module {
        prefix "p-ds-rf-port-perf";
        description 
            "File path: ds-rf-port-perf/ds-rf-port-perf-module.yang
            https://github.com/falcon-v-systems/rphy-yang-model/blob/master/r-phy-10/ds-rf-port-perf/ds-rf-port-perf-module.yang";
    }

    import ds-sc-qam-channel-config-module {
        prefix "p-ds-sc-qam-channel-config";
        description 
            "File path: ds-sc-qam-channel-config/ds-sc-qam-channel-config-module.yang
            https://github.com/falcon-v-systems/rphy-yang-model/blob/master/r-phy-10/ds-sc-qam-channel-config/ds-sc-qam-channel-config-module.yang";
    }

    import ds-sc-qam-channel-perf-module {
        prefix "p-ds-sc-qam-channel-perf";
        description 
            "File path: ds-sc-qam-channel-perf/ds-sc-qam-channel-perf-module.yang
            https://github.com/falcon-v-systems/rphy-yang-model/blob/master/r-phy-10/ds-sc-qam-channel-perf/ds-sc-qam-channel-perf-module.yang";
    }

    import enet-port-module {
        prefix "p-enet-port";
        description 
            "File path: enet-port/enet-port-module.yang
            https://github.com/falcon-v-systems/rphy-yang-model/blob/master/r-phy-10/enet-port/enet-port-module.yang";
    }

    import event-notification-module {
        prefix "p-event-notification";
        description 
            "File path: event-notification/event-notification-module.yang
            https://github.com/falcon-v-systems/rphy-yang-model/blob/master/r-phy-10/event-notification/event-notification-module.yang";
    }

    import gcp-handover-control-module {
        prefix "p-gcp-handover-control";
        description 
            "File path: gcp-handover-control/gcp-handover-control-module.yang
            https://github.com/falcon-v-systems/rphy-yang-model/blob/master/r-phy-10/gcp-handover-control/gcp-handover-control-module.yang";
    }

    import general-notification-module {
        prefix "p-general-notification";
        description 
            "File path: general-notification/general-notification-module.yang
            https://github.com/falcon-v-systems/rphy-yang-model/blob/master/r-phy-10/general-notification/general-notification-module.yang";
    }

    import ira-module {
        prefix "p-ira";
        description 
            "File path: ira/ira-module.yang
            https://github.com/falcon-v-systems/rphy-yang-model/blob/master/r-phy-10/ira/ira-module.yang";
    }

    import multi-core-module {
        prefix "p-multi-core";
        description 
            "File path: multi-core/multi-core-module.yang
            https://github.com/falcon-v-systems/rphy-yang-model/blob/master/r-phy-10/multi-core/multi-core-module.yang";
    }

    import ndf-config-module {
        prefix "p-ndf-config";
        description 
            "File path: ndf-config/ndf-config-module.yang
            https://github.com/falcon-v-systems/rphy-yang-model/blob/master/r-phy-10/ndf-config/ndf-config-module.yang";
    }

    import ndf-perf-module {
        prefix "p-ndf-perf";
        description 
            "File path: ndf-perf/ndf-perf-module.yang
            https://github.com/falcon-v-systems/rphy-yang-model/blob/master/r-phy-10/ndf-perf/ndf-perf-module.yang";
    }

    import ndr-config-module {
        prefix "p-ndr-config";
        description 
            "File path: ndr-config/ndr-config-module.yang
            https://github.com/falcon-v-systems/rphy-yang-model/blob/master/r-phy-10/ndr-config/ndr-config-module.yang";
    }

    import ndr-perf-module {
        prefix "p-ndr-perf";
        description 
            "File path: ndr-perf/ndr-perf-module.yang
            https://github.com/falcon-v-systems/rphy-yang-model/blob/master/r-phy-10/ndr-perf/ndr-perf-module.yang";
    }

    import ntf-module {
        prefix "p-ntf";
        description 
            "File path: ntf/ntf-module.yang
            https://github.com/falcon-v-systems/rphy-yang-model/blob/master/r-phy-10/ntf/ntf-module.yang";
    }

    import oob55d2-config-module {
        prefix "p-oob55d2-config";
        description 
            "File path: oob55d2-config/oob55d2-config-module.yang
            https://github.com/falcon-v-systems/rphy-yang-model/blob/master/r-phy-10/oob55d2-config/oob55d2-config-module.yang";
    }

    import output-buffer-occupancy-history-module {
        prefix "p-output-buffer-occupancy-history";
        description 
            "File path: output-buffer-occupancy-history/output-buffer-occupancy-history-module.yang
            https://github.com/falcon-v-systems/rphy-yang-model/blob/master/r-phy-10/output-buffer-occupancy-history/output-buffer-occupancy-history-module.yang";
    }

    import output-buffer-threshold-alert-module {
        prefix "p-output-buffer-threshold-alert";
        description 
            "File path: output-buffer-threshold-alert/output-buffer-threshold-alert-module.yang
            https://github.com/falcon-v-systems/rphy-yang-model/blob/master/r-phy-10/output-buffer-threshold-alert/output-buffer-threshold-alert-module.yang";
    }

    import pnm-us-histogram-module {
        prefix "p-pnm-us-histogram";
        description 
            "File path: pnm-us-histogram/pnm-us-histogram-module.yang
            https://github.com/falcon-v-systems/rphy-yang-model/blob/master/r-phy-10/pnm-us-histogram/pnm-us-histogram-module.yang";
    }

    import rdti-config-module {
        prefix "p-rdti-config";
        description 
            "File path: rdti-config/rdti-config-module.yang
            https://github.com/falcon-v-systems/rphy-yang-model/blob/master/r-phy-10/rdti-config/rdti-config-module.yang";
    }

    import rex-module {
        prefix "p-rex";
        description 
            "File path: rex/rex-module.yang
            https://github.com/falcon-v-systems/rphy-yang-model/blob/master/r-phy-10/rex/rex-module.yang";
    }

    import rf-channel-module {
        prefix "p-rf-channel";
        description 
            "File path: rf-channel/rf-channel-module.yang
            https://github.com/falcon-v-systems/rphy-yang-model/blob/master/r-phy-10/rf-channel/rf-channel-module.yang";
    }

    import rf-channel-selector-module {
        prefix "p-rf-channel-selector";
        description 
            "File path: rf-channel-selector/rf-channel-selector-module.yang
            https://github.com/falcon-v-systems/rphy-yang-model/blob/master/r-phy-10/rf-channel-selector/rf-channel-selector-module.yang";
    }

    import rf-port-module {
        prefix "p-rf-port";
        description 
            "File path: rf-port/rf-port-module.yang
            https://github.com/falcon-v-systems/rphy-yang-model/blob/master/r-phy-10/rf-port/rf-port-module.yang";
    }

    import rf-port-selector-module {
        prefix "p-rf-port-selector";
        description 
            "File path: rf-port-selector/rf-port-selector-module.yang
            https://github.com/falcon-v-systems/rphy-yang-model/blob/master/r-phy-10/rf-port-selector/rf-port-selector-module.yang";
    }

    import rpd-backup-core-status-table-module {
        prefix "p-rpd-backup-core-status-table";
        description 
            "File path: rpd-backup-core-status-table/rpd-backup-core-status-table-module.yang
            https://github.com/falcon-v-systems/rphy-yang-model/blob/master/r-phy-10/rpd-backup-core-status-table/rpd-backup-core-status-table-module.yang";
    }

    import rpd-capabilities-module {
        prefix "p-rpd-capabilities";
        description 
            "File path: rpd-capabilities/rpd-capabilities-module.yang
            https://github.com/falcon-v-systems/rphy-yang-model/blob/master/r-phy-10/rpd-capabilities/rpd-capabilities-module.yang";
    }

    import rpd-ctrl-module {
        prefix "p-rpd-ctrl";
        description 
            "File path: rpd-ctrl/rpd-ctrl-module.yang
            https://github.com/falcon-v-systems/rphy-yang-model/blob/master/r-phy-10/rpd-ctrl/rpd-ctrl-module.yang";
    }

    import rpd-gcp-connection-status-table-module {
        prefix "p-rpd-gcp-connection-status-table";
        description 
            "File path: rpd-gcp-connection-status-table/rpd-gcp-connection-status-table-module.yang
            https://github.com/falcon-v-systems/rphy-yang-model/blob/master/r-phy-10/rpd-gcp-connection-status-table/rpd-gcp-connection-status-table-module.yang";
    }

    import rpd-global-module {
        prefix "p-rpd-global";
        description 
            "File path: rpd-global/rpd-global-module.yang
            https://github.com/falcon-v-systems/rphy-yang-model/blob/master/r-phy-10/rpd-global/rpd-global-module.yang";
    }

    import rpd-hardware-status-module {
        prefix "p-rpd-hardware-status";
        description 
            "File path: rpd-hardware-status/rpd-hardware-status-module.yang
            https://github.com/falcon-v-systems/rphy-yang-model/blob/master/r-phy-10/rpd-hardware-status/rpd-hardware-status-module.yang";
    }

    import rpd-redirect-module {
        prefix "p-rpd-redirect";
        description 
            "File path: rpd-redirect/rpd-redirect-module.yang
            https://github.com/falcon-v-systems/rphy-yang-model/blob/master/r-phy-10/rpd-redirect/rpd-redirect-module.yang";
    }

    import rpd-state-module {
        prefix "p-rpd-state";
        description 
            "File path: rpd-state/rpd-state-module.yang
            https://github.com/falcon-v-systems/rphy-yang-model/blob/master/r-phy-10/rpd-state/rpd-state-module.yang";
    }

    import sequence-module {
        prefix "p-sequence";
        description 
            "File path: sequence/sequence-module.yang
            https://github.com/falcon-v-systems/rphy-yang-model/blob/master/r-phy-10/sequence/sequence-module.yang";
    }

    import sid-qos-module {
        prefix "p-sid-qos";
        description 
            "File path: sid-qos/sid-qos-module.yang
            https://github.com/falcon-v-systems/rphy-yang-model/blob/master/r-phy-10/sid-qos/sid-qos-module.yang";
    }

    import ssd-module {
        prefix "p-ssd";
        description 
            "File path: ssd/ssd-module.yang
            https://github.com/falcon-v-systems/rphy-yang-model/blob/master/r-phy-10/ssd/ssd-module.yang";
    }

    import static-pw-config-module {
        prefix "p-static-pw-config";
        description 
            "File path: static-pw-config/static-pw-config-module.yang
            https://github.com/falcon-v-systems/rphy-yang-model/blob/master/r-phy-10/static-pw-config/static-pw-config-module.yang";
    }

    import static-pw-status-module {
        prefix "p-static-pw-status";
        description 
            "File path: static-pw-status/static-pw-status-module.yang
            https://github.com/falcon-v-systems/rphy-yang-model/blob/master/r-phy-10/static-pw-status/static-pw-status-module.yang";
    }

    import time-of-day-module {
        prefix "p-time-of-day";
        description 
            "File path: time-of-day/time-of-day-module.yang
            https://github.com/falcon-v-systems/rphy-yang-model/blob/master/r-phy-10/time-of-day/time-of-day-module.yang";
    }

    import tlv-ext {
        prefix "tlv";
        description 
            "Falcon's Yang extension for TLV attributes.";
    }

    import us-ofdma-channel-config-module {
        prefix "p-us-ofdma-channel-config";
        description 
            "File path: us-ofdma-channel-config/us-ofdma-channel-config-module.yang
            https://github.com/falcon-v-systems/rphy-yang-model/blob/master/r-phy-10/us-ofdma-channel-config/us-ofdma-channel-config-module.yang";
    }

    import us-ofdma-channel-perf-module {
        prefix "p-us-ofdma-channel-perf";
        description 
            "File path: us-ofdma-channel-perf/us-ofdma-channel-perf-module.yang
            https://github.com/falcon-v-systems/rphy-yang-model/blob/master/r-phy-10/us-ofdma-channel-perf/us-ofdma-channel-perf-module.yang";
    }

    import us-ofdma-config-query-module {
        prefix "p-us-ofdma-config-query";
        description 
            "File path: us-ofdma-config-query/us-ofdma-config-query-module.yang
            https://github.com/falcon-v-systems/rphy-yang-model/blob/master/r-phy-10/us-ofdma-config-query/us-ofdma-config-query-module.yang";
    }

    import us-ofdma-config-response-module {
        prefix "p-us-ofdma-config-response";
        description 
            "File path: us-ofdma-config-response/us-ofdma-config-response-module.yang
            https://github.com/falcon-v-systems/rphy-yang-model/blob/master/r-phy-10/us-ofdma-config-response/us-ofdma-config-response-module.yang";
    }

    import us-ofdma-data-iuc-module {
        prefix "p-us-ofdma-data-iuc";
        description 
            "File path: us-ofdma-data-iuc/us-ofdma-data-iuc-module.yang
            https://github.com/falcon-v-systems/rphy-yang-model/blob/master/r-phy-10/us-ofdma-data-iuc/us-ofdma-data-iuc-module.yang";
    }

    import us-ofdma-fine-ranging-iuc-module {
        prefix "p-us-ofdma-fine-ranging-iuc";
        description 
            "File path: us-ofdma-fine-ranging-iuc/us-ofdma-fine-ranging-iuc-module.yang
            https://github.com/falcon-v-systems/rphy-yang-model/blob/master/r-phy-10/us-ofdma-fine-ranging-iuc/us-ofdma-fine-ranging-iuc-module.yang";
    }

    import us-ofdma-initial-ranging-iuc-module {
        prefix "p-us-ofdma-initial-ranging-iuc";
        description 
            "File path: us-ofdma-initial-ranging-iuc/us-ofdma-initial-ranging-iuc-module.yang
            https://github.com/falcon-v-systems/rphy-yang-model/blob/master/r-phy-10/us-ofdma-initial-ranging-iuc/us-ofdma-initial-ranging-iuc-module.yang";
    }

    import us-ofdma-subcarrier-cfg-module {
        prefix "p-us-ofdma-subcarrier-cfg";
        description 
            "File path: us-ofdma-subcarrier-cfg/us-ofdma-subcarrier-cfg-module.yang
            https://github.com/falcon-v-systems/rphy-yang-model/blob/master/r-phy-10/us-ofdma-subcarrier-cfg/us-ofdma-subcarrier-cfg-module.yang";
    }

    import us-oob551l-perf-module {
        prefix "p-us-oob551l-perf";
        description 
            "File path: us-oob551l-perf/us-oob551l-perf-module.yang
            https://github.com/falcon-v-systems/rphy-yang-model/blob/master/r-phy-10/us-oob551l-perf/us-oob551l-perf-module.yang";
    }

    import us-oob552-perf-module {
        prefix "p-us-oob552-perf";
        description 
            "File path: us-oob552-perf/us-oob552-perf-module.yang
            https://github.com/falcon-v-systems/rphy-yang-model/blob/master/r-phy-10/us-oob552-perf/us-oob552-perf-module.yang";
    }

    import us-oob55d1-module {
        prefix "p-us-oob55d1";
        description 
            "File path: us-oob55d1/us-oob55d1-module.yang
            https://github.com/falcon-v-systems/rphy-yang-model/blob/master/r-phy-10/us-oob55d1/us-oob55d1-module.yang";
    }

    import us-rf-port-module {
        prefix "p-us-rf-port";
        description 
            "File path: us-rf-port/us-rf-port-module.yang
            https://github.com/falcon-v-systems/rphy-yang-model/blob/master/r-phy-10/us-rf-port/us-rf-port-module.yang";
    }

    import us-rf-port-perf-module {
        prefix "p-us-rf-port-perf";
        description 
            "File path: us-rf-port-perf/us-rf-port-perf-module.yang
            https://github.com/falcon-v-systems/rphy-yang-model/blob/master/r-phy-10/us-rf-port-perf/us-rf-port-perf-module.yang";
    }

    import us-sc-qam-channel-config-module {
        prefix "p-us-sc-qam-channel-config";
        description 
            "File path: us-sc-qam-channel-config/us-sc-qam-channel-config-module.yang
            https://github.com/falcon-v-systems/rphy-yang-model/blob/master/r-phy-10/us-sc-qam-channel-config/us-sc-qam-channel-config-module.yang";
    }

    import us-sc-qam-channel-perf-module {
        prefix "p-us-sc-qam-channel-perf";
        description 
            "File path: us-sc-qam-channel-perf/us-sc-qam-channel-perf-module.yang
            https://github.com/falcon-v-systems/rphy-yang-model/blob/master/r-phy-10/us-sc-qam-channel-perf/us-sc-qam-channel-perf-module.yang";
    }

    import us-sc-qam-profile-query-module {
        prefix "p-us-sc-qam-profile-query";
        description 
            "File path: us-sc-qam-profile-query/us-sc-qam-profile-query-module.yang
            https://github.com/falcon-v-systems/rphy-yang-model/blob/master/r-phy-10/us-sc-qam-profile-query/us-sc-qam-profile-query-module.yang";
    }

    import us-sc-qam-profile-response-module {
        prefix "p-us-sc-qam-profile-response";
        description 
            "File path: us-sc-qam-profile-response/us-sc-qam-profile-response-module.yang
            https://github.com/falcon-v-systems/rphy-yang-model/blob/master/r-phy-10/us-sc-qam-profile-response/us-sc-qam-profile-response-module.yang";
    }

    import us-spectrum-capture-module {
        prefix "p-us-spectrum-capture";
        description 
            "File path: us-spectrum-capture/us-spectrum-capture-module.yang
            https://github.com/falcon-v-systems/rphy-yang-model/blob/master/r-phy-10/us-spectrum-capture/us-spectrum-capture-module.yang";
    }

    import vendor-specific-extension-module {
        prefix "p-vendor-specific-extension";
        description 
            "File path: vendor-specific-extension/vendor-specific-extension-module.yang
            https://github.com/falcon-v-systems/rphy-yang-model/blob/master/r-phy-10/vendor-specific-extension/vendor-specific-extension-module.yang";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

        container IRA {
            uses "p-ira:IRA-grouping";
            description
                "TLV [1]: IRA";
        }

        container REX {
            uses "p-rex:REX-grouping";
            description
                "TLV [2]: REX";
        }

        container NTF {
            uses "p-ntf:NTF-grouping";
            description
                "TLV [3]: NTF";
        }

        container Sequence {
            uses "p-sequence:Sequence-grouping";
            description
                "TLV [9]: Sequence";
        }

        leaf SequenceNumber {
            tlv:id 10;
            type uint16;
            description
                "TLV [10]: SequenceNumber";
        }

        leaf Operation {
            tlv:id 11;
            tlv:repr uint8;
            type enumeration {
                enum Read                     { value  1; description ""; }
                enum Write                    { value  2; description ""; }
                enum Delete                   { value  3; description ""; }
                enum ReadResponse             { value  4; description ""; }
                enum WriteResponse            { value  5; description ""; }
                enum DeleteResponse           { value  6; description ""; }
                enum AllocateWrite            { value  7; description ""; }
                enum AllocateWriteResponse    { value  8; description ""; }
            }
            description
                "TLV [11]: Operation";
        }

        container RfChannelSelector {
            uses "p-rf-channel-selector:RfChannelSelector-grouping";
            description
                "TLV [12]: RfChannelSelector";
        }

        container RfPortSelector {
            uses "p-rf-port-selector:RfPortSelector-grouping";
            description
                "TLV [13]: RfPortSelector";
        }

        leaf EnetPortIndex {
            tlv:id 14;
            type uint8;
            description
                "TLV [14]: EnetPortIndex";
        }

        container RfChannel {
            uses "p-rf-channel:RfChannel-grouping";
            description
                "TLV [16]: RfChannel";
        }

        container RfPort {
            uses "p-rf-port:RfPort-grouping";
            description
                "TLV [17]: RfPort";
        }

        container EnetPort {
            uses "p-enet-port:EnetPort-grouping";
            description
                "TLV [18]: EnetPort";
        }

        leaf ResponseCode {
            tlv:id 19;
            tlv:repr uint8;
            type enumeration {
                enum NoError                  { value  0; description ""; }
                enum GeneralError             { value  1; description ""; }
                enum ResponseTooBig           { value  2; description ""; }
                enum AttributeNotFound        { value  3; description ""; }
                enum BadIndex                 { value  4; description ""; }
                enum WriteToReadOnly          { value  5; description ""; }
                enum InconsistentValue        { value  6; description ""; }
                enum WrongLength              { value  7; description ""; }
                enum WrongValue               { value  8; description ""; }
                enum ResourceUnavailable      { value  9; description ""; }
                enum AuthorizationFailure     { value 10; description ""; }
                enum AttributeMissing         { value 11; description ""; }
                enum AllocationFailure        { value 12; description ""; }
                enum AllocationNoOwner        { value 13; description ""; }
                enum ErrorProcessingUCD       { value 14; description ""; }
                enum ErrorProcessingOCD       { value 15; description ""; }
                enum ErrorProcessingDPD       { value 16; description ""; }
            }
            description
                "TLV [19]: ResponseCode";
        }

        leaf ErrorMessage {
            tlv:id 20;
            type string;
            description
                "TLV [20]: ErrorMessage";
        }

        container VendorSpecificExtension {
            uses "p-vendor-specific-extension:VendorSpecificExtension-grouping";
            description
                "TLV [21]: VendorSpecificExtension";
        }

        leaf DocsisMsg {
            tlv:id 22;
            type binary;
            description
                "TLV [22]: DocsisMsg";
        }

        leaf DocsisTimestamp32 {
            tlv:id 23;
            type uint32;
            description
                "TLV [23]: DocsisTimestamp32";
        }

        leaf DocsisTimestamp64 {
            tlv:id 24;
            type uint64;
            description
                "TLV [24]: DocsisTimestamp64";
        }

        container RpdRedirect {
            uses "p-rpd-redirect:RpdRedirect-grouping";
            description
                "TLV [25]: RpdRedirect";
        }

        leaf ReadCount {
            tlv:id 26;
            type uint16;
            description
                "TLV [26]: ReadCount";
        }

        container RpdCapabilities {
            uses "p-rpd-capabilities:RpdCapabilities-grouping";
            description
                "TLV [50]: RpdCapabilities";
        }

        container RpdGlobal {
            uses "p-rpd-global:RpdGlobal-grouping";
            description
                "TLV [15]: RpdGlobal";
        }

        container CcapCoreIdentification {
            uses "p-ccap-core-identification:CcapCoreIdentification-grouping";
            description
                "TLV [60]: CcapCoreIdentification";
        }

        list DsRfPort {
            key PortIndex;
            uses "p-ds-rf-port:DsRfPort-grouping";
            description
                "List indexed with 1 key.
                 TLV [61]: DsRfPort";
        }

        list DsScQamChannelConfig {
            key Index;
            uses "p-ds-sc-qam-channel-config:DsScQamChannelConfig-grouping";
            description
                "List indexed with 1 key.
                 TLV [62]: DsScQamChannelConfig";
        }

        list DsOfdmChannelConfig {
            key Index;
            uses "p-ds-ofdm-channel-config:DsOfdmChannelConfig-grouping";
            description
                "List indexed with 1 key.
                 TLV [63]: DsOfdmChannelConfig";
        }

        list DsOfdmProfile {
            key ProfileId;
            uses "p-ds-ofdm-profile:DsOfdmProfile-grouping";
            description
                "List indexed with 1 key.
                 TLV [64]: DsOfdmProfile";
        }

        list UsScQamChannelConfig {
            key Index;
            uses "p-us-sc-qam-channel-config:UsScQamChannelConfig-grouping";
            description
                "List indexed with 1 key.
                 TLV [65]: UsScQamChannelConfig";
        }

        list UsOfdmaChannelConfig {
            key Index;
            uses "p-us-ofdma-channel-config:UsOfdmaChannelConfig-grouping";
            description
                "List indexed with 1 key.
                 TLV [66]: UsOfdmaChannelConfig";
        }

        container UsOfdmaInitialRangingIuc {
            uses "p-us-ofdma-initial-ranging-iuc:UsOfdmaInitialRangingIuc-grouping";
            description
                "TLV [67]: UsOfdmaInitialRangingIuc";
        }

        container UsOfdmaFineRangingIuc {
            uses "p-us-ofdma-fine-ranging-iuc:UsOfdmaFineRangingIuc-grouping";
            description
                "TLV [68]: UsOfdmaFineRangingIuc";
        }

        list UsOfdmaDataIuc {
            key DataIuc;
            uses "p-us-ofdma-data-iuc:UsOfdmaDataIuc-grouping";
            description
                "List indexed with 1 key.
                 TLV [69]: UsOfdmaDataIuc";
        }

        list UsOfdmaSubcarrierCfg {
            key StartingSubcarrierId;
            uses "p-us-ofdma-subcarrier-cfg:UsOfdmaSubcarrierCfg-grouping";
            description
                "List indexed with 1 key.
                 TLV [70]: UsOfdmaSubcarrierCfg";
        }

        list SidQos {
            key StartSid;
            uses "p-sid-qos:SidQos-grouping";
            description
                "List indexed with 1 key.
                 TLV [96]: SidQos";
        }

        list UsRfPort {
            key PortIndex;
            uses "p-us-rf-port:UsRfPort-grouping";
            description
                "List indexed with 1 key.
                 TLV [98]: UsRfPort";
        }

        container UsScQamProfileQuery {
            uses "p-us-sc-qam-profile-query:UsScQamProfileQuery-grouping";
            description
                "TLV [150]: UsScQamProfileQuery";
        }

        container UsScQamProfileResponse {
            uses "p-us-sc-qam-profile-response:UsScQamProfileResponse-grouping";
            description
                "TLV [151]: UsScQamProfileResponse";
        }

        container UsOfdmaConfigQuery {
            uses "p-us-ofdma-config-query:UsOfdmaConfigQuery-grouping";
            description
                "TLV [152]: UsOfdmaConfigQuery";
        }

        container UsOfdmaConfigResponse {
            uses "p-us-ofdma-config-response:UsOfdmaConfigResponse-grouping";
            description
                "TLV [153]: UsOfdmaConfigResponse";
        }

        container StaticPwConfig {
            uses "p-static-pw-config:StaticPwConfig-grouping";
            description
                "TLV [58]: StaticPwConfig";
        }

        container StaticPwStatus {
            uses "p-static-pw-status:StaticPwStatus-grouping";
            description
                "TLV [59]: StaticPwStatus";
        }

        container TimeOfDay {
            uses "p-time-of-day:TimeOfDay-grouping";
            description
                "TLV [104]: TimeOfDay";
        }

        list RpdGcpConnectionStatusTable {
            key Index;
            uses "p-rpd-gcp-connection-status-table:RpdGcpConnectionStatusTable-grouping";
            description
                "List indexed with 1 key.
                 TLV [105]: RpdGcpConnectionStatusTable";
        }

        container CoreGcpConnectionResponse {
            uses "p-core-gcp-connection-response:CoreGcpConnectionResponse-grouping";
            description
                "TLV [106]: CoreGcpConnectionResponse";
        }

        list RpdBackupCoreStatusTable {
            key Index;
            uses "p-rpd-backup-core-status-table:RpdBackupCoreStatusTable-grouping";
            description
                "List indexed with 1 key.
                 TLV [107]: RpdBackupCoreStatusTable";
        }

        leaf CoreGcpBackupResponse {
            tlv:id 108;
            tlv:repr uint8;
            type enumeration {
                enum noAction     { value  0; description ""; }
                enum Accept       { value  1; description ""; }
                enum Reject       { value  2; description ""; }
            }
            description
                "TLV [108]: CoreGcpBackupResponse";
        }

        container GcpHandoverControl {
            uses "p-gcp-handover-control:GcpHandoverControl-grouping";
            description
                "TLV [109]: GcpHandoverControl";
        }

        list DsRfPortPerf {
            key PortIndex;
            uses "p-ds-rf-port-perf:DsRfPortPerf-grouping";
            description
                "List indexed with 1 key.
                 TLV [71]: DsRfPortPerf";
        }

        list DsScQamChannelPerf {
            key Index;
            uses "p-ds-sc-qam-channel-perf:DsScQamChannelPerf-grouping";
            description
                "List indexed with 1 key.
                 TLV [72]: DsScQamChannelPerf";
        }

        list DsOfdmChannelPerf {
            key Index;
            uses "p-ds-ofdm-channel-perf:DsOfdmChannelPerf-grouping";
            description
                "List indexed with 1 key.
                 TLV [73]: DsOfdmChannelPerf";
        }

        container DsOob551lPerf {
            uses "p-ds-oob551l-perf:DsOob551lPerf-grouping";
            description
                "TLV [74]: DsOob551lPerf";
        }

        container DsOob552Perf {
            uses "p-ds-oob552-perf:DsOob552Perf-grouping";
            description
                "TLV [75]: DsOob552Perf";
        }

        list NdfPerf {
            key Index;
            uses "p-ndf-perf:NdfPerf-grouping";
            description
                "List indexed with 1 key.
                 TLV [76]: NdfPerf";
        }

        list UsRfPortPerf {
            key PortIndex;
            uses "p-us-rf-port-perf:UsRfPortPerf-grouping";
            description
                "List indexed with 1 key.
                 TLV [77]: UsRfPortPerf";
        }

        list UsScQamChannelPerf {
            key Index;
            uses "p-us-sc-qam-channel-perf:UsScQamChannelPerf-grouping";
            description
                "List indexed with 1 key.
                 TLV [78]: UsScQamChannelPerf";
        }

        list UsOfdmaChannelPerf {
            key Index;
            uses "p-us-ofdma-channel-perf:UsOfdmaChannelPerf-grouping";
            description
                "List indexed with 1 key.
                 TLV [79]: UsOfdmaChannelPerf";
        }

        container UsOob551lPerf {
            uses "p-us-oob551l-perf:UsOob551lPerf-grouping";
            description
                "TLV [80]: UsOob551lPerf";
        }

        container UsOob552Perf {
            uses "p-us-oob552-perf:UsOob552Perf-grouping";
            description
                "TLV [81]: UsOob552Perf";
        }

        list NdrPerf {
            key Index;
            uses "p-ndr-perf:NdrPerf-grouping";
            description
                "List indexed with 1 key.
                 TLV [82]: NdrPerf";
        }

        container RpdCtrl {
            uses "p-rpd-ctrl:RpdCtrl-grouping";
            description
                "TLV [40]: RpdCtrl";
        }

        container UsSpectrumCapture {
            uses "p-us-spectrum-capture:UsSpectrumCapture-grouping";
            description
                "TLV [41]: UsSpectrumCapture";
        }

        container Ssd {
            uses "p-ssd:Ssd-grouping";
            description
                "TLV [90]: Ssd";
        }

        container DsOob55d1 {
            uses "p-ds-oob55d1:DsOob55d1-grouping";
            description
                "TLV [91]: DsOob55d1";
        }

        list UsOob55d1 {
            key Index;
            uses "p-us-oob55d1:UsOob55d1-grouping";
            description
                "List indexed with 1 key.
                 TLV [92]: UsOob55d1";
        }

        container Oob55d2Config {
            uses "p-oob55d2-config:Oob55d2Config-grouping";
            description
                "TLV [93]: Oob55d2Config";
        }

        list NdfConfig {
            key Index;
            uses "p-ndf-config:NdfConfig-grouping";
            description
                "List indexed with 1 key.
                 TLV [94]: NdfConfig";
        }

        list NdrConfig {
            key Index;
            uses "p-ndr-config:NdrConfig-grouping";
            description
                "List indexed with 1 key.
                 TLV [95]: NdrConfig";
        }

        container RdtiConfig {
            uses "p-rdti-config:RdtiConfig-grouping";
            description
                "TLV [97]: RdtiConfig";
        }

        container DocsIf31 {
            uses "p-docs-if31:DocsIf31-grouping";
            description
                "TLV [101]: DocsIf31";
        }

        container DocsIf3 {
            uses "p-docs-if3:DocsIf3-grouping";
            description
                "TLV [102]: DocsIf3";
        }

        container DocsIf {
            uses "p-docs-if:DocsIf-grouping";
            description
                "TLV [103]: DocsIf";
        }

        container OutputBufferOccupancyHistory {
            uses "p-output-buffer-occupancy-history:OutputBufferOccupancyHistory-grouping";
            description
                "TLV [83]: OutputBufferOccupancyHistory";
        }

        container OutputBufferThresholdAlert {
            uses "p-output-buffer-threshold-alert:OutputBufferThresholdAlert-grouping";
            description
                "TLV [84]: OutputBufferThresholdAlert";
        }

        container EventNotification {
            uses "p-event-notification:EventNotification-grouping";
            description
                "TLV [85]: EventNotification";
        }

        container GeneralNotification {
            uses "p-general-notification:GeneralNotification-grouping";
            description
                "TLV [86]: GeneralNotification";
        }

        container RpdState {
            uses "p-rpd-state:RpdState-grouping";
            description
                "TLV [87]: RpdState";
        }

        container MultiCore {
            uses "p-multi-core:MultiCore-grouping";
            description
                "TLV [88]: MultiCore";
        }

        container RpdHardwareStatus {
            uses "p-rpd-hardware-status:RpdHardwareStatus-grouping";
            description
                "TLV [130]: RpdHardwareStatus";
        }

        container PnmUsHistogram {
            uses "p-pnm-us-histogram:PnmUsHistogram-grouping";
            description
                "TLV [131]: PnmUsHistogram";
        }

}
