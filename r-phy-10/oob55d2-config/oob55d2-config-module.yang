module oob55d2-config-module {
    yang-version 1;
    /* This file is automatically generated with Falcon V System's script.
       Any change made to this file will be lost. */

    namespace "falconvsystems:r-phy-10:oob55d2-config-module";
    prefix "p-oob55d2-config";

    // --- imports ---------------------------------------

    import ietf-yang-types {
        prefix "yang";
        description 
            "External YANG module.";
    }

    import oob55d2-module-module {
        prefix "p-oob55d2-module";
        description 
            "File path: oob55d2-config/oob55d2-module/oob55d2-module-module.yang
            https://github.com/falcon-v-systems/rphy-yang-model/blob/master/r-phy-10/oob55d2-config/oob55d2-module/oob55d2-module-module.yang";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-Oob55d2Config {
        tlv:id 93;
        description "TLV [93]: Oob55d2Config";
        leaf DsCenterFrequency {
            tlv:id 1;
            type uint32;
            units "Hz";
            description "TLV [93.1]: Oob55d2Config.DsCenterFrequency";
        }

        leaf UsCenterFrequency {
            tlv:id 2;
            type uint32;
            units "Hz";
            description "TLV [93.2]: Oob55d2Config.UsCenterFrequency";
        }

        leaf CcapCoreOwner {
            tlv:id 3;
            type yang:mac-address;
            description "TLV [93.3]: Oob55d2Config.CcapCoreOwner";
        }

        list Oob55d2Module {
            tlv:id 4;
            key ModuleIndex;
            description "TLV [93.4]: Oob55d2Config.Oob55d2Module";
            uses "p-oob55d2-module:g-Oob55d2Module";
        }

    }  // g-Oob55d2Config grouping

}
