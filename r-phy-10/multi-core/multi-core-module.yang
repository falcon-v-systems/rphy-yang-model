module multi-core-module {
    yang-version 1;
    /* This file is automatically generated with Falcon V System's script.
       Any change made to this file will be lost. */

    namespace "falconvsystems:r-phy-10:multi-core-module";
    prefix "p-multi-core";

    // --- imports ---------------------------------------

    import configured-core-table-module {
        prefix "p-configured-core-table";
        description 
            "File path: multi-core/configured-core-table/configured-core-table-module.yang
            https://github.com/falcon-v-systems/rphy-yang-model/blob/master/r-phy-10/multi-core/configured-core-table/configured-core-table-module.yang";
    }

    import down-channel-constraint-table-module {
        prefix "p-down-channel-constraint-table";
        description 
            "File path: multi-core/down-channel-constraint-table/down-channel-constraint-table-module.yang
            https://github.com/falcon-v-systems/rphy-yang-model/blob/master/r-phy-10/multi-core/down-channel-constraint-table/down-channel-constraint-table-module.yang";
    }

    import resource-set-module {
        prefix "p-resource-set";
        description 
            "File path: multi-core/resource-set/resource-set-module.yang
            https://github.com/falcon-v-systems/rphy-yang-model/blob/master/r-phy-10/multi-core/resource-set/resource-set-module.yang";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-MultiCore {
        tlv:id 88;
        description
            "TLV [88]: MultiCore
             non-defaults: [is_rcp_readonly: True, is_readonly: True]";
        container ConfiguredCoreTable {
            tlv:id 1;
            description
                "TLV [88.1]: MultiCore.ConfiguredCoreTable
                 non-defaults: [is_rcp_readonly: True, is_readonly: True]";
            uses "p-configured-core-table:g-ConfiguredCoreTable";
        }

        list ResourceSet {
            tlv:id 2;
            key ResourceSetIndex;
            description "TLV [88.2]: MultiCore.ResourceSet";
            uses "p-resource-set:g-ResourceSet";
        }

        leaf PermitAuxSelfConfiguration {
            tlv:id 3;
            type boolean;
            description "TLV [88.3]: MultiCore.PermitAuxSelfConfiguration";
        }

        list DownChannelConstraintTable {
            tlv:id 4;
            key Index;
            description
                "TLV [88.4]: MultiCore.DownChannelConstraintTable
                 non-defaults: [is_rcp_readonly: True, is_readonly: True]";
            uses "p-down-channel-constraint-table:g-DownChannelConstraintTable";
        }

        leaf ResourceAllocationCheck {
            tlv:id 5;
            type boolean;
            description "TLV [88.5]: MultiCore.ResourceAllocationCheck";
        }

    }  // g-MultiCore grouping

}
