module down-channel-constraint-table-module {
    yang-version 1;
    /* This file is automatically generated with Falcon V System's script.
       Any change made to this file will be lost. */

    namespace "falconvsystems:r-phy-10:down-channel-constraint-table-module";
    prefix "p-down-channel-constraint-table";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-DownChannelConstraintTable {
        tlv:id 4;
        description
            "TLV [88.4]: MultiCore.DownChannelConstraintTable
             non-defaults: [is_rcp_readonly: True, is_readonly: True]";
        leaf Index {
            tlv:id 1;
            type uint32;
            description
                "TLV [88.4.1]: MultiCore.DownChannelConstraintTable.Index
                 non-defaults: [is_key: True, is_rcp_readonly: True, is_readonly: True]";
        }

        leaf DownChanIndexStart {
            tlv:id 2;
            type uint32;
            description
                "TLV [88.4.2]: MultiCore.DownChannelConstraintTable.DownChanIndexStart
                 non-defaults: [is_rcp_readonly: True, is_readonly: True]";
        }

        leaf DownChanIndexEnd {
            tlv:id 3;
            type uint32;
            description
                "TLV [88.4.3]: MultiCore.DownChannelConstraintTable.DownChanIndexEnd
                 non-defaults: [is_rcp_readonly: True, is_readonly: True]";
        }

        leaf LockParameters {
            tlv:id 4;
            type binary;
            description
                "TLV [88.4.4]: MultiCore.DownChannelConstraintTable.LockParameters
                 non-defaults: [is_rcp_readonly: True, is_readonly: True]";
        }

    }  // g-DownChannelConstraintTable grouping

}
