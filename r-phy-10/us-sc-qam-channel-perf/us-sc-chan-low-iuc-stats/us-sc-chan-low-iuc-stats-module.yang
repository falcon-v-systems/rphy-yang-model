module us-sc-chan-low-iuc-stats-module {
    yang-version 1;
    /* This file is automatically generated with Falcon V System's script.
       Any change made to this file will be lost. */

    namespace "falconvsystems:r-phy-10:us-sc-chan-low-iuc-stats-module";
    prefix "p-us-sc-chan-low-iuc-stats";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-UsScChanLowIucStats {
        tlv:id 1;
        description "TLV [78.1]: UsScQamChannelPerf.UsScChanLowIucStats";
        leaf UsIuc {
            tlv:id 1;
            tlv:repr uint8;
            type enumeration {
                enum 1    { value  1; description ""; }
                enum 2    { value  2; description ""; }
                enum 3    { value  3; description ""; }
            }
            description "TLV [78.1.1]: UsScQamChannelPerf.UsScChanLowIucStats.UsIuc";
        }

        leaf UnicastOpportunities {
            tlv:id 2;
            type uint64;
            description
                "TLV [78.1.2]: UsScQamChannelPerf.UsScChanLowIucStats.UnicastOpportunities";
        }

        leaf UnicastOpCollisions {
            tlv:id 3;
            type uint64;
            description
                "TLV [78.1.3]: UsScQamChannelPerf.UsScChanLowIucStats.UnicastOpCollisions
                 non-defaults: [is_rcp_readonly: True, is_readonly: True]";
        }

        leaf UnicastOpNoEnergy {
            tlv:id 4;
            type uint64;
            description
                "TLV [78.1.4]: UsScQamChannelPerf.UsScChanLowIucStats.UnicastOpNoEnergy
                 non-defaults: [is_rcp_readonly: True, is_readonly: True]";
        }

        leaf UnicastOpErrors {
            tlv:id 5;
            type uint64;
            description
                "TLV [78.1.5]: UsScQamChannelPerf.UsScChanLowIucStats.UnicastOpErrors
                 non-defaults: [is_rcp_readonly: True, is_readonly: True]";
        }

        leaf MulticastOpportunities {
            tlv:id 6;
            type uint64;
            description
                "TLV [78.1.6]: UsScQamChannelPerf.UsScChanLowIucStats.MulticastOpportunities
                 non-defaults: [is_rcp_readonly: True, is_readonly: True]";
        }

        leaf McastOpCollisions {
            tlv:id 7;
            type uint64;
            description
                "TLV [78.1.7]: UsScQamChannelPerf.UsScChanLowIucStats.McastOpCollisions
                 non-defaults: [is_rcp_readonly: True, is_readonly: True]";
        }

        leaf McastOpNoEnergy {
            tlv:id 8;
            type uint64;
            description
                "TLV [78.1.8]: UsScQamChannelPerf.UsScChanLowIucStats.McastOpNoEnergy
                 non-defaults: [is_rcp_readonly: True, is_readonly: True]";
        }

        leaf McastOpErrors {
            tlv:id 9;
            type uint64;
            description
                "TLV [78.1.9]: UsScQamChannelPerf.UsScChanLowIucStats.McastOpErrors
                 non-defaults: [is_rcp_readonly: True, is_readonly: True]";
        }

        leaf GoodFecCw {
            tlv:id 10;
            type uint64;
            description
                "TLV [78.1.10]: UsScQamChannelPerf.UsScChanLowIucStats.GoodFecCw
                 non-defaults: [is_rcp_readonly: True, is_readonly: True]";
        }

        leaf CorrectedFecCw {
            tlv:id 11;
            type uint64;
            description
                "TLV [78.1.11]: UsScQamChannelPerf.UsScChanLowIucStats.CorrectedFecCw
                 non-defaults: [is_rcp_readonly: True, is_readonly: True]";
        }

        leaf UncorrectFecCw {
            tlv:id 12;
            type uint64;
            description
                "TLV [78.1.12]: UsScQamChannelPerf.UsScChanLowIucStats.UncorrectFecCw
                 non-defaults: [is_rcp_readonly: True, is_readonly: True]";
        }

    }  // g-UsScChanLowIucStats grouping

}
