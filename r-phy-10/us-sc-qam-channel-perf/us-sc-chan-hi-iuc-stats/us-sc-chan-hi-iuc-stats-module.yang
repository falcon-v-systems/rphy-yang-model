module us-sc-chan-hi-iuc-stats-module {
    yang-version 1;
    /* This file is automatically generated with Falcon V System's script.
       Any change made to this file will be lost. */

    namespace "falconvsystems:r-phy-10:us-sc-chan-hi-iuc-stats-module";
    prefix "p-us-sc-chan-hi-iuc-stats";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-UsScChanHiIucStats {
        tlv:id 2;
        description "TLV [78.2]: UsScQamChannelPerf.UsScChanHiIucStats";
        leaf UsIuc {
            tlv:id 1;
            tlv:repr uint8;
            type enumeration {
                enum 4    { value  4; description ""; }
                enum 5    { value  5; description ""; }
                enum 6    { value  6; description ""; }
                enum 9    { value  9; description ""; }
                enum 10   { value 10; description ""; }
                enum 11   { value 11; description ""; }
            }
            description "TLV [78.2.1]: UsScQamChannelPerf.UsScChanHiIucStats.UsIuc";
        }

        leaf ScheduledGrants {
            tlv:id 2;
            type uint64;
            description
                "TLV [78.2.2]: UsScQamChannelPerf.UsScChanHiIucStats.ScheduledGrants
                 non-defaults: [is_rcp_readonly: True, is_readonly: True]";
        }

        leaf NoEnergyBursts {
            tlv:id 3;
            type uint64;
            description
                "TLV [78.2.3]: UsScQamChannelPerf.UsScChanHiIucStats.NoEnergyBursts
                 non-defaults: [is_rcp_readonly: True, is_readonly: True]";
        }

        leaf NoPreambleBursts {
            tlv:id 4;
            type uint64;
            description
                "TLV [78.2.4]: UsScQamChannelPerf.UsScChanHiIucStats.NoPreambleBursts
                 non-defaults: [is_rcp_readonly: True, is_readonly: True]";
        }

        leaf ErrorBursts {
            tlv:id 5;
            type uint64;
            description
                "TLV [78.2.5]: UsScQamChannelPerf.UsScChanHiIucStats.ErrorBursts
                 non-defaults: [is_rcp_readonly: True, is_readonly: True]";
        }

        leaf GoodFecCw {
            tlv:id 6;
            type uint64;
            description
                "TLV [78.2.6]: UsScQamChannelPerf.UsScChanHiIucStats.GoodFecCw
                 non-defaults: [is_rcp_readonly: True, is_readonly: True]";
        }

        leaf CorrectedFecCw {
            tlv:id 7;
            type uint64;
            description
                "TLV [78.2.7]: UsScQamChannelPerf.UsScChanHiIucStats.CorrectedFecCw
                 non-defaults: [is_rcp_readonly: True, is_readonly: True]";
        }

        leaf UncorrectFecCw {
            tlv:id 8;
            type uint64;
            description
                "TLV [78.2.8]: UsScQamChannelPerf.UsScChanHiIucStats.UncorrectFecCw
                 non-defaults: [is_rcp_readonly: True, is_readonly: True]";
        }

    }  // g-UsScChanHiIucStats grouping

}
