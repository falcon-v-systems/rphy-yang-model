module us-rf-port-module {
    yang-version 1;
    /* This file is automatically generated with Falcon V System's script.
       Any change made to this file will be lost. */

    namespace "falconvsystems:r-phy-10:us-rf-port-module";
    prefix "p-us-rf-port";

    // --- imports ---------------------------------------

    import bw-req-aggr-control-module {
        prefix "p-bw-req-aggr-control";
        description 
            "File path: us-rf-port/bw-req-aggr-control/bw-req-aggr-control-module.yang
            https://github.com/falcon-v-systems/rphy-yang-model/blob/master/r-phy-10/us-rf-port/bw-req-aggr-control/bw-req-aggr-control-module.yang";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-UsRfPort {
        tlv:id 98;
        description "TLV [98]: UsRfPort";
        leaf PortIndex {
            // no tlv:id given
            type uint16;
            description
                "TLV [98.X]: UsRfPort.PortIndex
                 non-defaults: [is_key: True]";
        }

        leaf AdminState {
            tlv:id 1;
            tlv:repr uint8;
            type enumeration {
                enum other    { value  1; description ""; }
                enum up       { value  2; description ""; }
                enum down     { value  3; description ""; }
                enum testing  { value  4; description ""; }
            }
            description "TLV [98.1]: UsRfPort.AdminState";
        }

        container BwReqAggrControl {
            tlv:id 2;
            description "TLV [98.2]: UsRfPort.BwReqAggrControl";
            uses "p-bw-req-aggr-control:g-BwReqAggrControl";
        }

        leaf BaseTargetRxPower {
            tlv:id 3;
            type int16;
            description "TLV [98.3]: UsRfPort.BaseTargetRxPower";
        }

    }  // g-UsRfPort grouping

}
