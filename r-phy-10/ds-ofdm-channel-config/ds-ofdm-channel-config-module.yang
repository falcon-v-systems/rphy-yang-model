module ds-ofdm-channel-config-module {
    yang-version 1;
    /* This file is automatically generated with Falcon V System's script.
       Any change made to this file will be lost. */

    namespace "falconvsystems:r-phy-10:ds-ofdm-channel-config-module";
    prefix "p-ds-ofdm-channel-config";

    // --- imports ---------------------------------------

    import ds-ofdm-subcarrier-type-module {
        prefix "p-ds-ofdm-subcarrier-type";
        description 
            "File path: ds-ofdm-channel-config/ds-ofdm-subcarrier-type/ds-ofdm-subcarrier-type-module.yang
            https://github.com/falcon-v-systems/rphy-yang-model/blob/master/r-phy-10/ds-ofdm-channel-config/ds-ofdm-subcarrier-type/ds-ofdm-subcarrier-type-module.yang";
    }

    import ietf-yang-types {
        prefix "yang";
        description 
            "External YANG module.";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-DsOfdmChannelConfig {
        tlv:id 63;
        description "TLV [63]: DsOfdmChannelConfig";
        leaf Index {
            // no tlv:id given
            type uint16;
            description
                "TLV [63.X]: DsOfdmChannelConfig.Index
                 non-defaults: [is_key: True]";
        }

        leaf AdminState {
            tlv:id 1;
            tlv:repr uint8;
            type enumeration {
                enum other    { value  1; description ""; }
                enum up       { value  2; description ""; }
                enum down     { value  3; description ""; }
                enum testing  { value  4; description ""; }
            }
            description "TLV [63.1]: DsOfdmChannelConfig.AdminState";
        }

        leaf CcapCoreOwner {
            tlv:id 2;
            type yang:mac-address;
            description "TLV [63.2]: DsOfdmChannelConfig.CcapCoreOwner";
        }

        leaf RfMute {
            tlv:id 3;
            type boolean;
            description "TLV [63.3]: DsOfdmChannelConfig.RfMute";
        }

        leaf SubcarrierZeroFreq {
            tlv:id 4;
            type uint32;
            units "Hz";
            description
                "TLV [63.4]: DsOfdmChannelConfig.SubcarrierZeroFreq
                 non-defaults: [is_rcp_readonly: True]";
        }

        leaf FirstActiveSubcarrier {
            tlv:id 5;
            type uint16;
            description
                "TLV [63.5]: DsOfdmChannelConfig.FirstActiveSubcarrier
                 non-defaults: [is_rcp_readonly: True]";
        }

        leaf LastActiveSubcarrier {
            tlv:id 6;
            type uint16;
            description
                "TLV [63.6]: DsOfdmChannelConfig.LastActiveSubcarrier
                 non-defaults: [is_rcp_readonly: True]";
        }

        leaf NumActiveSubcarriers {
            tlv:id 7;
            type uint16;
            description
                "TLV [63.7]: DsOfdmChannelConfig.NumActiveSubcarriers
                 non-defaults: [is_rcp_readonly: True]";
        }

        leaf CyclicPrefix {
            tlv:id 8;
            tlv:repr uint8;
            type enumeration {
                enum 192      { value  1; description ""; }
                enum 256      { value  2; description ""; }
                enum 512      { value  3; description ""; }
                enum 768      { value  4; description ""; }
                enum 1024     { value  5; description ""; }
            }
            description
                "TLV [63.8]: DsOfdmChannelConfig.CyclicPrefix
                 non-defaults: [is_rcp_readonly: True]";
        }

        leaf RollOffPeriod {
            tlv:id 9;
            tlv:repr uint8;
            type enumeration {
                enum 0    { value  1; description ""; }
                enum 64   { value  2; description ""; }
                enum 128  { value  3; description ""; }
                enum 192  { value  4; description ""; }
                enum 256  { value  5; description ""; }
            }
            description
                "TLV [63.9]: DsOfdmChannelConfig.RollOffPeriod
                 non-defaults: [is_rcp_readonly: True]";
        }

        leaf PlcFreq {
            tlv:id 10;
            type uint32;
            units "Hz";
            description
                "TLV [63.10]: DsOfdmChannelConfig.PlcFreq
                 non-defaults: [is_rcp_readonly: True]";
        }

        leaf TimeInterleaverDepth {
            tlv:id 11;
            type uint8;
            description
                "TLV [63.11]: DsOfdmChannelConfig.TimeInterleaverDepth
                 non-defaults: [is_rcp_readonly: True]";
        }

        leaf SubcarrierSpacing {
            tlv:id 12;
            tlv:repr uint8;
            type enumeration {
                enum 25_KHz   { value  1; description ""; }
                enum 50_KHz   { value  2; description ""; }
            }
            description
                "TLV [63.12]: DsOfdmChannelConfig.SubcarrierSpacing
                 non-defaults: [is_rcp_readonly: True]";
        }

        list DsOfdmSubcarrierType {
            tlv:id 13;
            key StartSubcarrierId;
            description "TLV [63.13]: DsOfdmChannelConfig.DsOfdmSubcarrierType";
            uses "p-ds-ofdm-subcarrier-type:g-DsOfdmSubcarrierType";
        }

        leaf PowerAdjust {
            tlv:id 14;
            type int16;
            units "TenthdB";
            description "TLV [63.14]: DsOfdmChannelConfig.PowerAdjust";
        }

    }  // g-DsOfdmChannelConfig grouping

}
