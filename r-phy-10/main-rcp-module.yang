module main-rcp-module {
    yang-version 1;
    /* This file is automatically generated with Falcon V System's script.
       Any change made to this file will be lost. */

    namespace "falconvsystems:r-phy-10:main-rcp-module";
    prefix "p-main-rcp";

    // --- imports ---------------------------------------

    import ccap-core-identification-module {
        prefix "p-ccap-core-identification";
        description 
            "File path: ccap-core-identification/ccap-core-identification-module.yang
            https://github.com/falcon-v-systems/rphy-yang-model/blob/master/r-phy-10/ccap-core-identification/ccap-core-identification-module.yang";
    }

    import core-gcp-connection-response-module {
        prefix "p-core-gcp-connection-response";
        description 
            "File path: core-gcp-connection-response/core-gcp-connection-response-module.yang
            https://github.com/falcon-v-systems/rphy-yang-model/blob/master/r-phy-10/core-gcp-connection-response/core-gcp-connection-response-module.yang";
    }

    import docs-if-module {
        prefix "p-docs-if";
        description 
            "File path: docs-if/docs-if-module.yang
            https://github.com/falcon-v-systems/rphy-yang-model/blob/master/r-phy-10/docs-if/docs-if-module.yang";
    }

    import docs-if3-module {
        prefix "p-docs-if3";
        description 
            "File path: docs-if3/docs-if3-module.yang
            https://github.com/falcon-v-systems/rphy-yang-model/blob/master/r-phy-10/docs-if3/docs-if3-module.yang";
    }

    import docs-if31-module {
        prefix "p-docs-if31";
        description 
            "File path: docs-if31/docs-if31-module.yang
            https://github.com/falcon-v-systems/rphy-yang-model/blob/master/r-phy-10/docs-if31/docs-if31-module.yang";
    }

    import ds-ofdm-channel-config-module {
        prefix "p-ds-ofdm-channel-config";
        description 
            "File path: ds-ofdm-channel-config/ds-ofdm-channel-config-module.yang
            https://github.com/falcon-v-systems/rphy-yang-model/blob/master/r-phy-10/ds-ofdm-channel-config/ds-ofdm-channel-config-module.yang";
    }

    import ds-ofdm-channel-perf-module {
        prefix "p-ds-ofdm-channel-perf";
        description 
            "File path: ds-ofdm-channel-perf/ds-ofdm-channel-perf-module.yang
            https://github.com/falcon-v-systems/rphy-yang-model/blob/master/r-phy-10/ds-ofdm-channel-perf/ds-ofdm-channel-perf-module.yang";
    }

    import ds-ofdm-profile-module {
        prefix "p-ds-ofdm-profile";
        description 
            "File path: ds-ofdm-profile/ds-ofdm-profile-module.yang
            https://github.com/falcon-v-systems/rphy-yang-model/blob/master/r-phy-10/ds-ofdm-profile/ds-ofdm-profile-module.yang";
    }

    import ds-oob551l-perf-module {
        prefix "p-ds-oob551l-perf";
        description 
            "File path: ds-oob551l-perf/ds-oob551l-perf-module.yang
            https://github.com/falcon-v-systems/rphy-yang-model/blob/master/r-phy-10/ds-oob551l-perf/ds-oob551l-perf-module.yang";
    }

    import ds-oob552-perf-module {
        prefix "p-ds-oob552-perf";
        description 
            "File path: ds-oob552-perf/ds-oob552-perf-module.yang
            https://github.com/falcon-v-systems/rphy-yang-model/blob/master/r-phy-10/ds-oob552-perf/ds-oob552-perf-module.yang";
    }

    import ds-oob55d1-module {
        prefix "p-ds-oob55d1";
        description 
            "File path: ds-oob55d1/ds-oob55d1-module.yang
            https://github.com/falcon-v-systems/rphy-yang-model/blob/master/r-phy-10/ds-oob55d1/ds-oob55d1-module.yang";
    }

    import ds-rf-port-module {
        prefix "p-ds-rf-port";
        description 
            "File path: ds-rf-port/ds-rf-port-module.yang
            https://github.com/falcon-v-systems/rphy-yang-model/blob/master/r-phy-10/ds-rf-port/ds-rf-port-module.yang";
    }

    import ds-rf-port-perf-module {
        prefix "p-ds-rf-port-perf";
        description 
            "File path: ds-rf-port-perf/ds-rf-port-perf-module.yang
            https://github.com/falcon-v-systems/rphy-yang-model/blob/master/r-phy-10/ds-rf-port-perf/ds-rf-port-perf-module.yang";
    }

    import ds-sc-qam-channel-config-module {
        prefix "p-ds-sc-qam-channel-config";
        description 
            "File path: ds-sc-qam-channel-config/ds-sc-qam-channel-config-module.yang
            https://github.com/falcon-v-systems/rphy-yang-model/blob/master/r-phy-10/ds-sc-qam-channel-config/ds-sc-qam-channel-config-module.yang";
    }

    import ds-sc-qam-channel-perf-module {
        prefix "p-ds-sc-qam-channel-perf";
        description 
            "File path: ds-sc-qam-channel-perf/ds-sc-qam-channel-perf-module.yang
            https://github.com/falcon-v-systems/rphy-yang-model/blob/master/r-phy-10/ds-sc-qam-channel-perf/ds-sc-qam-channel-perf-module.yang";
    }

    import enet-port-module {
        prefix "p-enet-port";
        description 
            "File path: enet-port/enet-port-module.yang
            https://github.com/falcon-v-systems/rphy-yang-model/blob/master/r-phy-10/enet-port/enet-port-module.yang";
    }

    import event-notification-module {
        prefix "p-event-notification";
        description 
            "File path: event-notification/event-notification-module.yang
            https://github.com/falcon-v-systems/rphy-yang-model/blob/master/r-phy-10/event-notification/event-notification-module.yang";
    }

    import fft-module {
        prefix "p-fft";
        description 
            "File path: fft/fft-module.yang
            https://github.com/falcon-v-systems/rphy-yang-model/blob/master/r-phy-10/fft/fft-module.yang";
    }

    import gcp-handover-control-module {
        prefix "p-gcp-handover-control";
        description 
            "File path: gcp-handover-control/gcp-handover-control-module.yang
            https://github.com/falcon-v-systems/rphy-yang-model/blob/master/r-phy-10/gcp-handover-control/gcp-handover-control-module.yang";
    }

    import general-notification-module {
        prefix "p-general-notification";
        description 
            "File path: general-notification/general-notification-module.yang
            https://github.com/falcon-v-systems/rphy-yang-model/blob/master/r-phy-10/general-notification/general-notification-module.yang";
    }

    import ira-module {
        prefix "p-ira";
        description 
            "File path: ira/ira-module.yang
            https://github.com/falcon-v-systems/rphy-yang-model/blob/master/r-phy-10/ira/ira-module.yang";
    }

    import multi-core-module {
        prefix "p-multi-core";
        description 
            "File path: multi-core/multi-core-module.yang
            https://github.com/falcon-v-systems/rphy-yang-model/blob/master/r-phy-10/multi-core/multi-core-module.yang";
    }

    import ndf-config-module {
        prefix "p-ndf-config";
        description 
            "File path: ndf-config/ndf-config-module.yang
            https://github.com/falcon-v-systems/rphy-yang-model/blob/master/r-phy-10/ndf-config/ndf-config-module.yang";
    }

    import ndf-perf-module {
        prefix "p-ndf-perf";
        description 
            "File path: ndf-perf/ndf-perf-module.yang
            https://github.com/falcon-v-systems/rphy-yang-model/blob/master/r-phy-10/ndf-perf/ndf-perf-module.yang";
    }

    import ndr-config-module {
        prefix "p-ndr-config";
        description 
            "File path: ndr-config/ndr-config-module.yang
            https://github.com/falcon-v-systems/rphy-yang-model/blob/master/r-phy-10/ndr-config/ndr-config-module.yang";
    }

    import ndr-perf-module {
        prefix "p-ndr-perf";
        description 
            "File path: ndr-perf/ndr-perf-module.yang
            https://github.com/falcon-v-systems/rphy-yang-model/blob/master/r-phy-10/ndr-perf/ndr-perf-module.yang";
    }

    import ntf-module {
        prefix "p-ntf";
        description 
            "File path: ntf/ntf-module.yang
            https://github.com/falcon-v-systems/rphy-yang-model/blob/master/r-phy-10/ntf/ntf-module.yang";
    }

    import oob55d2-config-module {
        prefix "p-oob55d2-config";
        description 
            "File path: oob55d2-config/oob55d2-config-module.yang
            https://github.com/falcon-v-systems/rphy-yang-model/blob/master/r-phy-10/oob55d2-config/oob55d2-config-module.yang";
    }

    import output-buffer-occupancy-history-module {
        prefix "p-output-buffer-occupancy-history";
        description 
            "File path: output-buffer-occupancy-history/output-buffer-occupancy-history-module.yang
            https://github.com/falcon-v-systems/rphy-yang-model/blob/master/r-phy-10/output-buffer-occupancy-history/output-buffer-occupancy-history-module.yang";
    }

    import output-buffer-threshold-alert-module {
        prefix "p-output-buffer-threshold-alert";
        description 
            "File path: output-buffer-threshold-alert/output-buffer-threshold-alert-module.yang
            https://github.com/falcon-v-systems/rphy-yang-model/blob/master/r-phy-10/output-buffer-threshold-alert/output-buffer-threshold-alert-module.yang";
    }

    import pnm-us-histogram-module {
        prefix "p-pnm-us-histogram";
        description 
            "File path: pnm-us-histogram/pnm-us-histogram-module.yang
            https://github.com/falcon-v-systems/rphy-yang-model/blob/master/r-phy-10/pnm-us-histogram/pnm-us-histogram-module.yang";
    }

    import rdti-config-module {
        prefix "p-rdti-config";
        description 
            "File path: rdti-config/rdti-config-module.yang
            https://github.com/falcon-v-systems/rphy-yang-model/blob/master/r-phy-10/rdti-config/rdti-config-module.yang";
    }

    import rex-module {
        prefix "p-rex";
        description 
            "File path: rex/rex-module.yang
            https://github.com/falcon-v-systems/rphy-yang-model/blob/master/r-phy-10/rex/rex-module.yang";
    }

    import rf-channel-module {
        prefix "p-rf-channel";
        description 
            "File path: rf-channel/rf-channel-module.yang
            https://github.com/falcon-v-systems/rphy-yang-model/blob/master/r-phy-10/rf-channel/rf-channel-module.yang";
    }

    import rf-channel-selector-module {
        prefix "p-rf-channel-selector";
        description 
            "File path: rf-channel-selector/rf-channel-selector-module.yang
            https://github.com/falcon-v-systems/rphy-yang-model/blob/master/r-phy-10/rf-channel-selector/rf-channel-selector-module.yang";
    }

    import rf-port-module {
        prefix "p-rf-port";
        description 
            "File path: rf-port/rf-port-module.yang
            https://github.com/falcon-v-systems/rphy-yang-model/blob/master/r-phy-10/rf-port/rf-port-module.yang";
    }

    import rf-port-selector-module {
        prefix "p-rf-port-selector";
        description 
            "File path: rf-port-selector/rf-port-selector-module.yang
            https://github.com/falcon-v-systems/rphy-yang-model/blob/master/r-phy-10/rf-port-selector/rf-port-selector-module.yang";
    }

    import rpd-backup-core-status-table-module {
        prefix "p-rpd-backup-core-status-table";
        description 
            "File path: rpd-backup-core-status-table/rpd-backup-core-status-table-module.yang
            https://github.com/falcon-v-systems/rphy-yang-model/blob/master/r-phy-10/rpd-backup-core-status-table/rpd-backup-core-status-table-module.yang";
    }

    import rpd-capabilities-module {
        prefix "p-rpd-capabilities";
        description 
            "File path: rpd-capabilities/rpd-capabilities-module.yang
            https://github.com/falcon-v-systems/rphy-yang-model/blob/master/r-phy-10/rpd-capabilities/rpd-capabilities-module.yang";
    }

    import rpd-ctrl-module {
        prefix "p-rpd-ctrl";
        description 
            "File path: rpd-ctrl/rpd-ctrl-module.yang
            https://github.com/falcon-v-systems/rphy-yang-model/blob/master/r-phy-10/rpd-ctrl/rpd-ctrl-module.yang";
    }

    import rpd-gcp-connection-status-table-module {
        prefix "p-rpd-gcp-connection-status-table";
        description 
            "File path: rpd-gcp-connection-status-table/rpd-gcp-connection-status-table-module.yang
            https://github.com/falcon-v-systems/rphy-yang-model/blob/master/r-phy-10/rpd-gcp-connection-status-table/rpd-gcp-connection-status-table-module.yang";
    }

    import rpd-global-module {
        prefix "p-rpd-global";
        description 
            "File path: rpd-global/rpd-global-module.yang
            https://github.com/falcon-v-systems/rphy-yang-model/blob/master/r-phy-10/rpd-global/rpd-global-module.yang";
    }

    import rpd-hardware-status-module {
        prefix "p-rpd-hardware-status";
        description 
            "File path: rpd-hardware-status/rpd-hardware-status-module.yang
            https://github.com/falcon-v-systems/rphy-yang-model/blob/master/r-phy-10/rpd-hardware-status/rpd-hardware-status-module.yang";
    }

    import rpd-info-module {
        prefix "p-rpd-info";
        description 
            "File path: rpd-info/rpd-info-module.yang
            https://github.com/falcon-v-systems/rphy-yang-model/blob/master/r-phy-10/rpd-info/rpd-info-module.yang";
    }

    import rpd-redirect-module {
        prefix "p-rpd-redirect";
        description 
            "File path: rpd-redirect/rpd-redirect-module.yang
            https://github.com/falcon-v-systems/rphy-yang-model/blob/master/r-phy-10/rpd-redirect/rpd-redirect-module.yang";
    }

    import rpd-state-module {
        prefix "p-rpd-state";
        description 
            "File path: rpd-state/rpd-state-module.yang
            https://github.com/falcon-v-systems/rphy-yang-model/blob/master/r-phy-10/rpd-state/rpd-state-module.yang";
    }

    import sid-qos-module {
        prefix "p-sid-qos";
        description 
            "File path: sid-qos/sid-qos-module.yang
            https://github.com/falcon-v-systems/rphy-yang-model/blob/master/r-phy-10/sid-qos/sid-qos-module.yang";
    }

    import ssd-module {
        prefix "p-ssd";
        description 
            "File path: ssd/ssd-module.yang
            https://github.com/falcon-v-systems/rphy-yang-model/blob/master/r-phy-10/ssd/ssd-module.yang";
    }

    import static-pw-config-module {
        prefix "p-static-pw-config";
        description 
            "File path: static-pw-config/static-pw-config-module.yang
            https://github.com/falcon-v-systems/rphy-yang-model/blob/master/r-phy-10/static-pw-config/static-pw-config-module.yang";
    }

    import static-pw-status-module {
        prefix "p-static-pw-status";
        description 
            "File path: static-pw-status/static-pw-status-module.yang
            https://github.com/falcon-v-systems/rphy-yang-model/blob/master/r-phy-10/static-pw-status/static-pw-status-module.yang";
    }

    import time-of-day-module {
        prefix "p-time-of-day";
        description 
            "File path: time-of-day/time-of-day-module.yang
            https://github.com/falcon-v-systems/rphy-yang-model/blob/master/r-phy-10/time-of-day/time-of-day-module.yang";
    }

    import tlv-ext {
        prefix "tlv";
        description 
            "Falcon's Yang extension for TLV attributes.";
    }

    import us-ofdma-channel-config-module {
        prefix "p-us-ofdma-channel-config";
        description 
            "File path: us-ofdma-channel-config/us-ofdma-channel-config-module.yang
            https://github.com/falcon-v-systems/rphy-yang-model/blob/master/r-phy-10/us-ofdma-channel-config/us-ofdma-channel-config-module.yang";
    }

    import us-ofdma-channel-perf-module {
        prefix "p-us-ofdma-channel-perf";
        description 
            "File path: us-ofdma-channel-perf/us-ofdma-channel-perf-module.yang
            https://github.com/falcon-v-systems/rphy-yang-model/blob/master/r-phy-10/us-ofdma-channel-perf/us-ofdma-channel-perf-module.yang";
    }

    import us-ofdma-config-query-module {
        prefix "p-us-ofdma-config-query";
        description 
            "File path: us-ofdma-config-query/us-ofdma-config-query-module.yang
            https://github.com/falcon-v-systems/rphy-yang-model/blob/master/r-phy-10/us-ofdma-config-query/us-ofdma-config-query-module.yang";
    }

    import us-ofdma-config-response-module {
        prefix "p-us-ofdma-config-response";
        description 
            "File path: us-ofdma-config-response/us-ofdma-config-response-module.yang
            https://github.com/falcon-v-systems/rphy-yang-model/blob/master/r-phy-10/us-ofdma-config-response/us-ofdma-config-response-module.yang";
    }

    import us-ofdma-data-iuc-module {
        prefix "p-us-ofdma-data-iuc";
        description 
            "File path: us-ofdma-data-iuc/us-ofdma-data-iuc-module.yang
            https://github.com/falcon-v-systems/rphy-yang-model/blob/master/r-phy-10/us-ofdma-data-iuc/us-ofdma-data-iuc-module.yang";
    }

    import us-ofdma-fine-ranging-iuc-module {
        prefix "p-us-ofdma-fine-ranging-iuc";
        description 
            "File path: us-ofdma-fine-ranging-iuc/us-ofdma-fine-ranging-iuc-module.yang
            https://github.com/falcon-v-systems/rphy-yang-model/blob/master/r-phy-10/us-ofdma-fine-ranging-iuc/us-ofdma-fine-ranging-iuc-module.yang";
    }

    import us-ofdma-initial-ranging-iuc-module {
        prefix "p-us-ofdma-initial-ranging-iuc";
        description 
            "File path: us-ofdma-initial-ranging-iuc/us-ofdma-initial-ranging-iuc-module.yang
            https://github.com/falcon-v-systems/rphy-yang-model/blob/master/r-phy-10/us-ofdma-initial-ranging-iuc/us-ofdma-initial-ranging-iuc-module.yang";
    }

    import us-ofdma-subcarrier-cfg-module {
        prefix "p-us-ofdma-subcarrier-cfg";
        description 
            "File path: us-ofdma-subcarrier-cfg/us-ofdma-subcarrier-cfg-module.yang
            https://github.com/falcon-v-systems/rphy-yang-model/blob/master/r-phy-10/us-ofdma-subcarrier-cfg/us-ofdma-subcarrier-cfg-module.yang";
    }

    import us-oob551l-perf-module {
        prefix "p-us-oob551l-perf";
        description 
            "File path: us-oob551l-perf/us-oob551l-perf-module.yang
            https://github.com/falcon-v-systems/rphy-yang-model/blob/master/r-phy-10/us-oob551l-perf/us-oob551l-perf-module.yang";
    }

    import us-oob552-perf-module {
        prefix "p-us-oob552-perf";
        description 
            "File path: us-oob552-perf/us-oob552-perf-module.yang
            https://github.com/falcon-v-systems/rphy-yang-model/blob/master/r-phy-10/us-oob552-perf/us-oob552-perf-module.yang";
    }

    import us-oob55d1-module {
        prefix "p-us-oob55d1";
        description 
            "File path: us-oob55d1/us-oob55d1-module.yang
            https://github.com/falcon-v-systems/rphy-yang-model/blob/master/r-phy-10/us-oob55d1/us-oob55d1-module.yang";
    }

    import us-rf-port-module {
        prefix "p-us-rf-port";
        description 
            "File path: us-rf-port/us-rf-port-module.yang
            https://github.com/falcon-v-systems/rphy-yang-model/blob/master/r-phy-10/us-rf-port/us-rf-port-module.yang";
    }

    import us-rf-port-perf-module {
        prefix "p-us-rf-port-perf";
        description 
            "File path: us-rf-port-perf/us-rf-port-perf-module.yang
            https://github.com/falcon-v-systems/rphy-yang-model/blob/master/r-phy-10/us-rf-port-perf/us-rf-port-perf-module.yang";
    }

    import us-sc-qam-channel-config-module {
        prefix "p-us-sc-qam-channel-config";
        description 
            "File path: us-sc-qam-channel-config/us-sc-qam-channel-config-module.yang
            https://github.com/falcon-v-systems/rphy-yang-model/blob/master/r-phy-10/us-sc-qam-channel-config/us-sc-qam-channel-config-module.yang";
    }

    import us-sc-qam-channel-perf-module {
        prefix "p-us-sc-qam-channel-perf";
        description 
            "File path: us-sc-qam-channel-perf/us-sc-qam-channel-perf-module.yang
            https://github.com/falcon-v-systems/rphy-yang-model/blob/master/r-phy-10/us-sc-qam-channel-perf/us-sc-qam-channel-perf-module.yang";
    }

    import us-sc-qam-profile-query-module {
        prefix "p-us-sc-qam-profile-query";
        description 
            "File path: us-sc-qam-profile-query/us-sc-qam-profile-query-module.yang
            https://github.com/falcon-v-systems/rphy-yang-model/blob/master/r-phy-10/us-sc-qam-profile-query/us-sc-qam-profile-query-module.yang";
    }

    import us-sc-qam-profile-response-module {
        prefix "p-us-sc-qam-profile-response";
        description 
            "File path: us-sc-qam-profile-response/us-sc-qam-profile-response-module.yang
            https://github.com/falcon-v-systems/rphy-yang-model/blob/master/r-phy-10/us-sc-qam-profile-response/us-sc-qam-profile-response-module.yang";
    }

    import us-spectrum-capture-module {
        prefix "p-us-spectrum-capture";
        description 
            "File path: us-spectrum-capture/us-spectrum-capture-module.yang
            https://github.com/falcon-v-systems/rphy-yang-model/blob/master/r-phy-10/us-spectrum-capture/us-spectrum-capture-module.yang";
    }

    import vendor-specific-extension-module {
        prefix "p-vendor-specific-extension";
        description 
            "File path: vendor-specific-extension/vendor-specific-extension-module.yang
            https://github.com/falcon-v-systems/rphy-yang-model/blob/master/r-phy-10/vendor-specific-extension/vendor-specific-extension-module.yang";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    leaf RpdPtpClockStatus {
        tlv:id 51;
        type uint8;
        description
            "TLV [51]: RpdPtpClockStatus
             non-defaults: [is_readonly: True]";
    }

    leaf RpdConfigurationDone {
        tlv:id 52;
        type uint8;
        description
            "TLV [52]: RpdConfigurationDone
             non-defaults: [is_readonly: True]";
    }

    container Fft {
        tlv:id 99;
        description
            "TLV [99]: Fft
             non-defaults: [is_readonly: True]";
        uses "p-fft:g-Fft";
    }

    container RpdInfo {
        tlv:id 100;
        description "TLV [100]: RpdInfo";
        uses "p-rpd-info:g-RpdInfo";
    }

    container IRA {
        tlv:id 1;
        description "TLV [1]: IRA";
        uses "p-ira:g-IRA";
    }

    container REX {
        tlv:id 2;
        description "TLV [2]: REX";
        uses "p-rex:g-REX";
    }

    container NTF {
        tlv:id 3;
        description "TLV [3]: NTF";
        uses "p-ntf:g-NTF";
    }

    leaf Operation {
        tlv:id 11;
        tlv:repr uint8;
        type enumeration {
            enum Read                     { value  1; description ""; }
            enum Write                    { value  2; description ""; }
            enum Delete                   { value  3; description ""; }
            enum ReadResponse             { value  4; description ""; }
            enum WriteResponse            { value  5; description ""; }
            enum DeleteResponse           { value  6; description ""; }
            enum AllocateWrite            { value  7; description ""; }
            enum AllocateWriteResponse    { value  8; description ""; }
        }
        description "TLV [11]: Operation";
    }

    container RfChannelSelector {
        tlv:id 12;
        description "TLV [12]: RfChannelSelector";
        uses "p-rf-channel-selector:g-RfChannelSelector";
    }

    container RfPortSelector {
        tlv:id 13;
        description "TLV [13]: RfPortSelector";
        uses "p-rf-port-selector:g-RfPortSelector";
    }

    leaf EnetPortIndex {
        tlv:id 14;
        type uint8;
        description "TLV [14]: EnetPortIndex";
    }

    container RfChannel {
        tlv:id 16;
        description "TLV [16]: RfChannel";
        uses "p-rf-channel:g-RfChannel";
    }

    container RfPort {
        tlv:id 17;
        description "TLV [17]: RfPort";
        uses "p-rf-port:g-RfPort";
    }

    container EnetPort {
        tlv:id 18;
        description "TLV [18]: EnetPort";
        uses "p-enet-port:g-EnetPort";
    }

    leaf ResponseCode {
        tlv:id 19;
        tlv:repr uint8;
        type enumeration {
            enum NoError                  { value  0; description ""; }
            enum GeneralError             { value  1; description ""; }
            enum ResponseTooBig           { value  2; description ""; }
            enum AttributeNotFound        { value  3; description ""; }
            enum BadIndex                 { value  4; description ""; }
            enum WriteToReadOnly          { value  5; description ""; }
            enum InconsistentValue        { value  6; description ""; }
            enum WrongLength              { value  7; description ""; }
            enum WrongValue               { value  8; description ""; }
            enum ResourceUnavailable      { value  9; description ""; }
            enum AuthorizationFailure     { value 10; description ""; }
            enum AttributeMissing         { value 11; description ""; }
            enum AllocationFailure        { value 12; description ""; }
            enum AllocationNoOwner        { value 13; description ""; }
            enum ErrorProcessingUCD       { value 14; description ""; }
            enum ErrorProcessingOCD       { value 15; description ""; }
            enum ErrorProcessingDPD       { value 16; description ""; }
        }
        description "TLV [19]: ResponseCode";
    }

    leaf ErrorMessage {
        tlv:id 20;
        type string;
        description "TLV [20]: ErrorMessage";
    }

    container VendorSpecificExtension {
        tlv:id 21;
        description "TLV [21]: VendorSpecificExtension";
        uses "p-vendor-specific-extension:g-VendorSpecificExtension";
    }

    leaf DocsisMsg {
        tlv:id 22;
        type binary;
        description "TLV [22]: DocsisMsg";
    }

    leaf DocsisTimestamp32 {
        tlv:id 23;
        type uint32;
        description "TLV [23]: DocsisTimestamp32";
    }

    leaf DocsisTimestamp64 {
        tlv:id 24;
        type uint64;
        description "TLV [24]: DocsisTimestamp64";
    }

    container RpdRedirect {
        tlv:id 25;
        description "TLV [25]: RpdRedirect";
        uses "p-rpd-redirect:g-RpdRedirect";
    }

    leaf ReadCount {
        tlv:id 26;
        type uint16;
        description "TLV [26]: ReadCount";
    }

    container RpdCapabilities {
        tlv:id 50;
        description
            "TLV [50]: RpdCapabilities
             non-defaults: [is_rcp_readonly: True, is_readonly: True]";
        uses "p-rpd-capabilities:g-RpdCapabilities";
    }

    container RpdGlobal {
        tlv:id 15;
        description "TLV [15]: RpdGlobal";
        uses "p-rpd-global:g-RpdGlobal";
    }

    container CcapCoreIdentification {
        tlv:id 60;
        description "TLV [60]: CcapCoreIdentification";
        uses "p-ccap-core-identification:g-CcapCoreIdentification";
    }

    list DsRfPort {
        tlv:id 61;
        key PortIndex;
        description "TLV [61]: DsRfPort";
        uses "p-ds-rf-port:g-DsRfPort";
    }

    list DsScQamChannelConfig {
        tlv:id 62;
        key Index;
        description "TLV [62]: DsScQamChannelConfig";
        uses "p-ds-sc-qam-channel-config:g-DsScQamChannelConfig";
    }

    list DsOfdmChannelConfig {
        tlv:id 63;
        key Index;
        description "TLV [63]: DsOfdmChannelConfig";
        uses "p-ds-ofdm-channel-config:g-DsOfdmChannelConfig";
    }

    list DsOfdmProfile {
        tlv:id 64;
        key ProfileId;
        description "TLV [64]: DsOfdmProfile";
        uses "p-ds-ofdm-profile:g-DsOfdmProfile";
    }

    list UsScQamChannelConfig {
        tlv:id 65;
        key Index;
        description "TLV [65]: UsScQamChannelConfig";
        uses "p-us-sc-qam-channel-config:g-UsScQamChannelConfig";
    }

    list UsOfdmaChannelConfig {
        tlv:id 66;
        key Index;
        description "TLV [66]: UsOfdmaChannelConfig";
        uses "p-us-ofdma-channel-config:g-UsOfdmaChannelConfig";
    }

    container UsOfdmaInitialRangingIuc {
        tlv:id 67;
        description "TLV [67]: UsOfdmaInitialRangingIuc";
        uses "p-us-ofdma-initial-ranging-iuc:g-UsOfdmaInitialRangingIuc";
    }

    container UsOfdmaFineRangingIuc {
        tlv:id 68;
        description "TLV [68]: UsOfdmaFineRangingIuc";
        uses "p-us-ofdma-fine-ranging-iuc:g-UsOfdmaFineRangingIuc";
    }

    list UsOfdmaDataIuc {
        tlv:id 69;
        key DataIuc;
        description "TLV [69]: UsOfdmaDataIuc";
        uses "p-us-ofdma-data-iuc:g-UsOfdmaDataIuc";
    }

    list UsOfdmaSubcarrierCfg {
        tlv:id 70;
        key StartingSubcarrierId;
        description "TLV [70]: UsOfdmaSubcarrierCfg";
        uses "p-us-ofdma-subcarrier-cfg:g-UsOfdmaSubcarrierCfg";
    }

    list SidQos {
        tlv:id 96;
        key StartSid;
        description "TLV [96]: SidQos";
        uses "p-sid-qos:g-SidQos";
    }

    list UsRfPort {
        tlv:id 98;
        key PortIndex;
        description "TLV [98]: UsRfPort";
        uses "p-us-rf-port:g-UsRfPort";
    }

    container UsScQamProfileQuery {
        tlv:id 150;
        description "TLV [150]: UsScQamProfileQuery";
        uses "p-us-sc-qam-profile-query:g-UsScQamProfileQuery";
    }

    container UsScQamProfileResponse {
        tlv:id 151;
        description
            "TLV [151]: UsScQamProfileResponse
             non-defaults: [is_rcp_readonly: True]";
        uses "p-us-sc-qam-profile-response:g-UsScQamProfileResponse";
    }

    container UsOfdmaConfigQuery {
        tlv:id 152;
        description "TLV [152]: UsOfdmaConfigQuery";
        uses "p-us-ofdma-config-query:g-UsOfdmaConfigQuery";
    }

    container UsOfdmaConfigResponse {
        tlv:id 153;
        description
            "TLV [153]: UsOfdmaConfigResponse
             non-defaults: [is_rcp_readonly: True]";
        uses "p-us-ofdma-config-response:g-UsOfdmaConfigResponse";
    }

    container StaticPwConfig {
        tlv:id 58;
        description "TLV [58]: StaticPwConfig";
        uses "p-static-pw-config:g-StaticPwConfig";
    }

    container StaticPwStatus {
        tlv:id 59;
        description "TLV [59]: StaticPwStatus";
        uses "p-static-pw-status:g-StaticPwStatus";
    }

    container TimeOfDay {
        tlv:id 104;
        description "TLV [104]: TimeOfDay";
        uses "p-time-of-day:g-TimeOfDay";
    }

    list RpdGcpConnectionStatusTable {
        tlv:id 105;
        key Index;
        description "TLV [105]: RpdGcpConnectionStatusTable";
        uses "p-rpd-gcp-connection-status-table:g-RpdGcpConnectionStatusTable";
    }

    container CoreGcpConnectionResponse {
        tlv:id 106;
        description "TLV [106]: CoreGcpConnectionResponse";
        uses "p-core-gcp-connection-response:g-CoreGcpConnectionResponse";
    }

    list RpdBackupCoreStatusTable {
        tlv:id 107;
        key Index;
        description "TLV [107]: RpdBackupCoreStatusTable";
        uses "p-rpd-backup-core-status-table:g-RpdBackupCoreStatusTable";
    }

    leaf CoreGcpBackupResponse {
        tlv:id 108;
        tlv:repr uint8;
        type enumeration {
            enum noAction     { value  0; description ""; }
            enum Accept       { value  1; description ""; }
            enum Reject       { value  2; description ""; }
        }
        description "TLV [108]: CoreGcpBackupResponse";
    }

    container GcpHandoverControl {
        tlv:id 109;
        description "TLV [109]: GcpHandoverControl";
        uses "p-gcp-handover-control:g-GcpHandoverControl";
    }

    list DsRfPortPerf {
        tlv:id 71;
        key PortIndex;
        description
            "TLV [71]: DsRfPortPerf
             non-defaults: [is_rcp_readonly: True, is_readonly: True]";
        uses "p-ds-rf-port-perf:g-DsRfPortPerf";
    }

    list DsScQamChannelPerf {
        tlv:id 72;
        key Index;
        description
            "TLV [72]: DsScQamChannelPerf
             non-defaults: [is_rcp_readonly: True, is_readonly: True]";
        uses "p-ds-sc-qam-channel-perf:g-DsScQamChannelPerf";
    }

    list DsOfdmChannelPerf {
        tlv:id 73;
        key Index;
        description
            "TLV [73]: DsOfdmChannelPerf
             non-defaults: [is_rcp_readonly: True, is_readonly: True]";
        uses "p-ds-ofdm-channel-perf:g-DsOfdmChannelPerf";
    }

    container DsOob551lPerf {
        tlv:id 74;
        description
            "TLV [74]: DsOob551lPerf
             non-defaults: [is_rcp_readonly: True, is_readonly: True]";
        uses "p-ds-oob551l-perf:g-DsOob551lPerf";
    }

    container DsOob552Perf {
        tlv:id 75;
        description
            "TLV [75]: DsOob552Perf
             non-defaults: [is_rcp_readonly: True, is_readonly: True]";
        uses "p-ds-oob552-perf:g-DsOob552Perf";
    }

    list NdfPerf {
        tlv:id 76;
        key Index;
        description
            "TLV [76]: NdfPerf
             non-defaults: [is_rcp_readonly: True, is_readonly: True]";
        uses "p-ndf-perf:g-NdfPerf";
    }

    list UsRfPortPerf {
        tlv:id 77;
        key PortIndex;
        description
            "TLV [77]: UsRfPortPerf
             non-defaults: [is_rcp_readonly: True, is_readonly: True]";
        uses "p-us-rf-port-perf:g-UsRfPortPerf";
    }

    list UsScQamChannelPerf {
        tlv:id 78;
        key Index;
        description
            "TLV [78]: UsScQamChannelPerf
             non-defaults: [is_rcp_readonly: True, is_readonly: True]";
        uses "p-us-sc-qam-channel-perf:g-UsScQamChannelPerf";
    }

    list UsOfdmaChannelPerf {
        tlv:id 79;
        key Index;
        description "TLV [79]: UsOfdmaChannelPerf";
        uses "p-us-ofdma-channel-perf:g-UsOfdmaChannelPerf";
    }

    container UsOob551lPerf {
        tlv:id 80;
        description
            "TLV [80]: UsOob551lPerf
             non-defaults: [is_rcp_readonly: True, is_readonly: True]";
        uses "p-us-oob551l-perf:g-UsOob551lPerf";
    }

    container UsOob552Perf {
        tlv:id 81;
        description
            "TLV [81]: UsOob552Perf
             non-defaults: [is_rcp_readonly: True, is_readonly: True]";
        uses "p-us-oob552-perf:g-UsOob552Perf";
    }

    list NdrPerf {
        tlv:id 82;
        key Index;
        description
            "TLV [82]: NdrPerf
             non-defaults: [is_rcp_readonly: True, is_readonly: True]";
        uses "p-ndr-perf:g-NdrPerf";
    }

    container RpdCtrl {
        tlv:id 40;
        description "TLV [40]: RpdCtrl";
        uses "p-rpd-ctrl:g-RpdCtrl";
    }

    container UsSpectrumCapture {
        tlv:id 41;
        description "TLV [41]: UsSpectrumCapture";
        uses "p-us-spectrum-capture:g-UsSpectrumCapture";
    }

    container Ssd {
        tlv:id 90;
        description "TLV [90]: Ssd";
        uses "p-ssd:g-Ssd";
    }

    container DsOob55d1 {
        tlv:id 91;
        description "TLV [91]: DsOob55d1";
        uses "p-ds-oob55d1:g-DsOob55d1";
    }

    list UsOob55d1 {
        tlv:id 92;
        key Index;
        description "TLV [92]: UsOob55d1";
        uses "p-us-oob55d1:g-UsOob55d1";
    }

    container Oob55d2Config {
        tlv:id 93;
        description "TLV [93]: Oob55d2Config";
        uses "p-oob55d2-config:g-Oob55d2Config";
    }

    list NdfConfig {
        tlv:id 94;
        key Index;
        description "TLV [94]: NdfConfig";
        uses "p-ndf-config:g-NdfConfig";
    }

    list NdrConfig {
        tlv:id 95;
        key Index;
        description "TLV [95]: NdrConfig";
        uses "p-ndr-config:g-NdrConfig";
    }

    container RdtiConfig {
        tlv:id 97;
        description "TLV [97]: RdtiConfig";
        uses "p-rdti-config:g-RdtiConfig";
    }

    container DocsIf31 {
        tlv:id 101;
        description
            "TLV [101]: DocsIf31
             non-defaults: [is_rcp_readonly: True, is_readonly: True]";
        uses "p-docs-if31:g-DocsIf31";
    }

    container DocsIf3 {
        tlv:id 102;
        description
            "TLV [102]: DocsIf3
             non-defaults: [is_rcp_readonly: True, is_readonly: True]";
        uses "p-docs-if3:g-DocsIf3";
    }

    container DocsIf {
        tlv:id 103;
        description
            "TLV [103]: DocsIf
             non-defaults: [is_rcp_readonly: True, is_readonly: True]";
        uses "p-docs-if:g-DocsIf";
    }

    container OutputBufferOccupancyHistory {
        tlv:id 83;
        description "TLV [83]: OutputBufferOccupancyHistory";
        uses "p-output-buffer-occupancy-history:g-OutputBufferOccupancyHistory";
    }

    container OutputBufferThresholdAlert {
        tlv:id 84;
        description "TLV [84]: OutputBufferThresholdAlert";
        uses "p-output-buffer-threshold-alert:g-OutputBufferThresholdAlert";
    }

    container EventNotification {
        tlv:id 85;
        description "TLV [85]: EventNotification";
        uses "p-event-notification:g-EventNotification";
    }

    container GeneralNotification {
        tlv:id 86;
        description "TLV [86]: GeneralNotification";
        uses "p-general-notification:g-GeneralNotification";
    }

    container RpdState {
        tlv:id 87;
        description
            "TLV [87]: RpdState
             non-defaults: [is_rcp_readonly: True, is_readonly: True]";
        uses "p-rpd-state:g-RpdState";
    }

    container MultiCore {
        tlv:id 88;
        description
            "TLV [88]: MultiCore
             non-defaults: [is_rcp_readonly: True, is_readonly: True]";
        uses "p-multi-core:g-MultiCore";
    }

    container RpdHardwareStatus {
        tlv:id 130;
        description "TLV [130]: RpdHardwareStatus";
        uses "p-rpd-hardware-status:g-RpdHardwareStatus";
    }

    container PnmUsHistogram {
        tlv:id 131;
        description "TLV [131]: PnmUsHistogram";
        uses "p-pnm-us-histogram:g-PnmUsHistogram";
    }

}
