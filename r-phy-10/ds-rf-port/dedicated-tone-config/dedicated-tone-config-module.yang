module dedicated-tone-config-module {
    yang-version 1;
    /* This file is automatically generated with Falcon V System's script.
       Any change made to this file will be lost. */

    namespace "falconvsystems:r-phy-10:dedicated-tone-config-module";
    prefix "p-dedicated-tone-config";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-DedicatedToneConfig {
        tlv:id 7;
        description "TLV [61.7]: DsRfPort.DedicatedToneConfig";
        leaf ToneIndex {
            tlv:id 1;
            type uint8;
            description
                "TLV [61.7.1]: DsRfPort.DedicatedToneConfig.ToneIndex
                 non-defaults: [is_key: True]";
        }

        leaf ToneFrequency {
            tlv:id 2;
            type uint32;
            units "Hz";
            description "TLV [61.7.2]: DsRfPort.DedicatedToneConfig.ToneFrequency";
        }

        leaf TonePowerAdjust {
            tlv:id 3;
            type int16;
            units "TenthdB";
            description "TLV [61.7.3]: DsRfPort.DedicatedToneConfig.TonePowerAdjust";
        }

        leaf RfMute {
            tlv:id 4;
            type boolean;
            description "TLV [61.7.4]: DsRfPort.DedicatedToneConfig.RfMute";
        }

        leaf FrequencyFraction {
            tlv:id 5;
            type uint8;
            units "TenthHz";
            description "TLV [61.7.5]: DsRfPort.DedicatedToneConfig.FrequencyFraction";
        }

    }  // g-DedicatedToneConfig grouping

}
