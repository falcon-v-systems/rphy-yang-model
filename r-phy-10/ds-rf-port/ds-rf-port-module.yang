module ds-rf-port-module {
    yang-version 1;
    /* This file is automatically generated with Falcon V System's script.
       Any change made to this file will be lost. */

    namespace "falconvsystems:r-phy-10:ds-rf-port-module";
    prefix "p-ds-rf-port";

    // --- imports ---------------------------------------

    import dedicated-tone-config-module {
        prefix "p-dedicated-tone-config";
        description 
            "File path: ds-rf-port/dedicated-tone-config/dedicated-tone-config-module.yang
            https://github.com/falcon-v-systems/rphy-yang-model/blob/master/r-phy-10/ds-rf-port/dedicated-tone-config/dedicated-tone-config-module.yang";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-DsRfPort {
        tlv:id 61;
        description "TLV [61]: DsRfPort";
        leaf PortIndex {
            // no tlv:id given
            type uint16;
            description
                "TLV [61.X]: DsRfPort.PortIndex
                 non-defaults: [is_key: True]";
        }

        leaf AdminState {
            tlv:id 2;
            tlv:repr uint8;
            type enumeration {
                enum other    { value  1; description ""; }
                enum up       { value  2; description ""; }
                enum down     { value  3; description ""; }
                enum testing  { value  4; description ""; }
            }
            description "TLV [61.2]: DsRfPort.AdminState";
        }

        leaf BasePower {
            tlv:id 3;
            type int16;
            units "TenthdBmV";
            description "TLV [61.3]: DsRfPort.BasePower";
        }

        leaf RfMute {
            tlv:id 4;
            type boolean;
            description "TLV [61.4]: DsRfPort.RfMute";
        }

        leaf TiltValue {
            tlv:id 5;
            type int16;
            units "TenthdB";
            description "TLV [61.5]: DsRfPort.TiltValue";
        }

        leaf TiltMaximumFrequency {
            tlv:id 6;
            type uint32;
            units "Hz";
            description "TLV [61.6]: DsRfPort.TiltMaximumFrequency";
        }

        list DedicatedToneConfig {
            tlv:id 7;
            key ToneIndex;
            description "TLV [61.7]: DsRfPort.DedicatedToneConfig";
            uses "p-dedicated-tone-config:g-DedicatedToneConfig";
        }

    }  // g-DsRfPort grouping

}
