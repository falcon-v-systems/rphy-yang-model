module rpd-global-module {
    yang-version 1;
    /* This file is automatically generated with Falcon V System's script.
       Any change made to this file will be lost. */

    namespace "falconvsystems:r-phy-10:rpd-global-module";
    prefix "p-rpd-global";

    // --- imports ---------------------------------------

    import ev-cfg-module {
        prefix "p-ev-cfg";
        description 
            "File path: rpd-global/ev-cfg/ev-cfg-module.yang
            https://github.com/falcon-v-systems/rphy-yang-model/blob/master/r-phy-10/rpd-global/ev-cfg/ev-cfg-module.yang";
    }

    import gcp-conn-verification-module {
        prefix "p-gcp-conn-verification";
        description 
            "File path: rpd-global/gcp-conn-verification/gcp-conn-verification-module.yang
            https://github.com/falcon-v-systems/rphy-yang-model/blob/master/r-phy-10/rpd-global/gcp-conn-verification/gcp-conn-verification-module.yang";
    }

    import ip-config-module {
        prefix "p-ip-config";
        description 
            "File path: rpd-global/ip-config/ip-config-module.yang
            https://github.com/falcon-v-systems/rphy-yang-model/blob/master/r-phy-10/rpd-global/ip-config/ip-config-module.yang";
    }

    import tlv-ext {
        prefix "tlv";
        description 
            "Falcon's Yang extension for TLV attributes.";
    }

    import uepi-control-module {
        prefix "p-uepi-control";
        description 
            "File path: rpd-global/uepi-control/uepi-control-module.yang
            https://github.com/falcon-v-systems/rphy-yang-model/blob/master/r-phy-10/rpd-global/uepi-control/uepi-control-module.yang";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-RpdGlobal {
        tlv:id 15;
        description "TLV [15]: RpdGlobal";
        container EvCfg {
            tlv:id 1;
            description "TLV [15.1]: RpdGlobal.EvCfg";
            uses "p-ev-cfg:g-EvCfg";
        }

        container GcpConnVerification {
            tlv:id 2;
            description "TLV [15.2]: RpdGlobal.GcpConnVerification";
            uses "p-gcp-conn-verification:g-GcpConnVerification";
        }

        container IpConfig {
            tlv:id 3;
            description "TLV [15.3]: RpdGlobal.IpConfig";
            uses "p-ip-config:g-IpConfig";
        }

        container UepiControl {
            tlv:id 4;
            description "TLV [15.4]: RpdGlobal.UepiControl";
            uses "p-uepi-control:g-UepiControl";
        }

        leaf GcpDscp {
            tlv:id 5;
            type uint8;
            description "TLV [15.5]: RpdGlobal.GcpDscp";
        }

    }  // g-RpdGlobal grouping

}
