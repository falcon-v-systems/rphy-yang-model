module ev-control-module {
    yang-version 1;
    /* This file is automatically generated with Falcon V System's script.
       Any change made to this file will be lost. */

    namespace "falconvsystems:r-phy-10:ev-control-module";
    prefix "p-ev-control";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-EvControl {
        tlv:id 1;
        description "TLV [15.1.1]: RpdGlobal.EvCfg.EvControl";
        leaf EvPriority {
            tlv:id 1;
            tlv:repr uint8;
            type enumeration {
                enum emergency    { value  1; description ""; }
                enum alert        { value  2; description ""; }
                enum critical     { value  3; description ""; }
                enum error        { value  4; description ""; }
                enum warning      { value  5; description ""; }
                enum notice       { value  6; description ""; }
                enum information  { value  7; description ""; }
                enum debug        { value  8; description ""; }
            }
            description
                "TLV [15.1.1.1]: RpdGlobal.EvCfg.EvControl.EvPriority
                 non-defaults: [is_key: True]";
        }

        leaf EvReporting {
            tlv:id 2;
            tlv:repr uint8;
            type enumeration {
                enum None         { value  0; description ""; }
                enum Local        { value  1; description ""; }
                enum GCP          { value  2; description ""; }
                enum LocalAndGCP  { value  3; description ""; }
            }
            description "TLV [15.1.1.2]: RpdGlobal.EvCfg.EvControl.EvReporting";
        }

    }  // g-EvControl grouping

}
