module gcp-conn-verification-module {
    yang-version 1;
    /* This file is automatically generated with Falcon V System's script.
       Any change made to this file will be lost. */

    namespace "falconvsystems:r-phy-10:gcp-conn-verification-module";
    prefix "p-gcp-conn-verification";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-GcpConnVerification {
        tlv:id 2;
        description "TLV [15.2]: RpdGlobal.GcpConnVerification";
        leaf CoreId {
            tlv:id 1;
            type binary;
            description "TLV [15.2.1]: RpdGlobal.GcpConnVerification.CoreId";
        }

        leaf MaxGcpIdleTime {
            tlv:id 2;
            type uint16;
            units "seconds";
            description "TLV [15.2.2]: RpdGlobal.GcpConnVerification.MaxGcpIdleTime";
        }

        leaf GcpRecoveryAction {
            tlv:id 3;
            tlv:repr uint8;
            type enumeration {
                enum GcpWaitForReconnectFromCore  { value  1; description ""; }
                enum GcpReconnectToTheSameCore    { value  2; description ""; }
                enum GcpReconnectToBackupCore     { value  3; description ""; }
                enum WaitAndReboot                { value  4; description ""; }
            }
            description
                "TLV [15.2.3]: RpdGlobal.GcpConnVerification.GcpRecoveryAction";
        }

        leaf GcpRecoveryActionRetry {
            tlv:id 4;
            type uint8;
            description
                "TLV [15.2.4]: RpdGlobal.GcpConnVerification.GcpRecoveryActionRetry";
        }

        leaf GcpRecoveryActionDelay {
            tlv:id 5;
            type uint16;
            units "seconds";
            description
                "TLV [15.2.5]: RpdGlobal.GcpConnVerification.GcpRecoveryActionDelay";
        }

        leaf GcpReconnectTimeout {
            tlv:id 6;
            type uint16;
            units "seconds";
            description
                "TLV [15.2.6]: RpdGlobal.GcpConnVerification.GcpReconnectTimeout";
        }

        leaf GcpHandoverTimeout {
            tlv:id 7;
            type uint16;
            units "seconds";
            description
                "TLV [15.2.7]: RpdGlobal.GcpConnVerification.GcpHandoverTimeout";
        }

    }  // g-GcpConnVerification grouping

}
