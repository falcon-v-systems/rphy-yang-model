module candidate-backup-core-table-module {
    yang-version 1;
    /* This file is automatically generated with Falcon V System's script.
       Any change made to this file will be lost. */

    namespace "falconvsystems:r-phy-10:candidate-backup-core-table-module";
    prefix "p-candidate-backup-core-table";

    // --- imports ---------------------------------------

    import ietf-inet-types {
        prefix "inet";
        description 
            "External YANG module.";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-CandidateBackupCoreTable {
        tlv:id 14;
        description "TLV [60.14]: CcapCoreIdentification.CandidateBackupCoreTable";
        leaf Index {
            tlv:id 1;
            type uint8;
            description
                "TLV [60.14.1]: CcapCoreIdentification.CandidateBackupCoreTable.Index";
        }

        leaf BackupCoreIpAddress {
            tlv:id 2;
            type inet:ip-address;
            description
                "TLV [60.14.2]: CcapCoreIdentification.CandidateBackupCoreTable.BackupCoreIpAddress";
        }

    }  // g-CandidateBackupCoreTable grouping

}
