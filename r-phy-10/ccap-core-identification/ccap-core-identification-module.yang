module ccap-core-identification-module {
    yang-version 1;
    /* This file is automatically generated with Falcon V System's script.
       Any change made to this file will be lost. */

    namespace "falconvsystems:r-phy-10:ccap-core-identification-module";
    prefix "p-ccap-core-identification";

    // --- imports ---------------------------------------

    import candidate-backup-core-table-module {
        prefix "p-candidate-backup-core-table";
        description 
            "File path: ccap-core-identification/candidate-backup-core-table/candidate-backup-core-table-module.yang
            https://github.com/falcon-v-systems/rphy-yang-model/blob/master/r-phy-10/ccap-core-identification/candidate-backup-core-table/candidate-backup-core-table-module.yang";
    }

    import ietf-inet-types {
        prefix "inet";
        description 
            "External YANG module.";
    }

    import ietf-yang-types {
        prefix "yang";
        description 
            "External YANG module.";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-CcapCoreIdentification {
        tlv:id 60;
        description "TLV [60]: CcapCoreIdentification";
        leaf Index {
            tlv:id 1;
            type uint8;
            description "TLV [60.1]: CcapCoreIdentification.Index";
        }

        leaf CoreId {
            tlv:id 2;
            type yang:mac-address;
            description "TLV [60.2]: CcapCoreIdentification.CoreId";
        }

        leaf CoreIpAddress {
            tlv:id 3;
            type inet:ip-address;
            description "TLV [60.3]: CcapCoreIdentification.CoreIpAddress";
        }

        leaf IsPrincipal {
            tlv:id 4;
            type boolean;
            description "TLV [60.4]: CcapCoreIdentification.IsPrincipal";
        }

        leaf CoreName {
            tlv:id 5;
            type string;
            description "TLV [60.5]: CcapCoreIdentification.CoreName";
        }

        leaf VendorId {
            tlv:id 6;
            type uint16;
            description "TLV [60.6]: CcapCoreIdentification.VendorId";
        }

        leaf CoreMode {
            tlv:id 7;
            tlv:repr uint8;
            type enumeration {
                enum Active           { value  1; description ""; }
                enum Backup           { value  2; description ""; }
                enum NotActing        { value  3; description ""; }
                enum DecisionPending  { value  4; description ""; }
                enum OutOfService     { value  5; description ""; }
                enum ContactPending   { value  6; description ""; }
                enum Reconnecting     { value  7; description ""; }
            }
            description "TLV [60.7]: CcapCoreIdentification.CoreMode";
        }

        leaf InitialConfigurationComplete {
            tlv:id 8;
            type boolean;
            description
                "TLV [60.8]: CcapCoreIdentification.InitialConfigurationComplete";
        }

        leaf MoveToOperational {
            tlv:id 9;
            type boolean;
            description "TLV [60.9]: CcapCoreIdentification.MoveToOperational";
        }

        leaf CoreFunction {
            tlv:id 10;
            type uint16;
            description "TLV [60.10]: CcapCoreIdentification.CoreFunction";
        }

        leaf ResourceSetIndex {
            tlv:id 11;
            type uint8;
            description "TLV [60.11]: CcapCoreIdentification.ResourceSetIndex";
        }

        leaf Deprecated {
            tlv:id 12;
            type uint16;
            description "TLV [60.12]: CcapCoreIdentification.Deprecated";
        }

        leaf GcpBackupConnectionConfig {
            tlv:id 13;
            type uint16;
            description
                "TLV [60.13]: CcapCoreIdentification.GcpBackupConnectionConfig";
        }

        container CandidateBackupCoreTable {
            tlv:id 14;
            description "TLV [60.14]: CcapCoreIdentification.CandidateBackupCoreTable";
            uses "p-candidate-backup-core-table:g-CandidateBackupCoreTable";
        }

    }  // g-CcapCoreIdentification grouping

}
