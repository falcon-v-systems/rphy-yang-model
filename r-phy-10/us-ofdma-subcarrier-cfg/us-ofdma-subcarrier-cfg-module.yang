module us-ofdma-subcarrier-cfg-module {
    yang-version 1;
    /* This file is automatically generated with Falcon V System's script.
       Any change made to this file will be lost. */

    namespace "falconvsystems:r-phy-10:us-ofdma-subcarrier-cfg-module";
    prefix "p-us-ofdma-subcarrier-cfg";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-UsOfdmaSubcarrierCfg {
        tlv:id 70;
        description "TLV [70]: UsOfdmaSubcarrierCfg";
        leaf StartingSubcarrierId {
            tlv:id 1;
            type uint16;
            description
                "TLV [70.1]: UsOfdmaSubcarrierCfg.StartingSubcarrierId
                 non-defaults: [is_key: True, is_rcp_readonly: True]";
        }

        leaf NumConsecutiveSubcarriers {
            tlv:id 2;
            type uint16;
            description
                "TLV [70.2]: UsOfdmaSubcarrierCfg.NumConsecutiveSubcarriers
                 non-defaults: [is_rcp_readonly: True]";
        }

        leaf SubcarrierUsage {
            tlv:id 3;
            tlv:repr uint8;
            type enumeration {
                enum Other        { value  1; description ""; }
                enum Data         { value  2; description ""; }
                enum Excluded     { value  3; description ""; }
                enum Unused       { value  4; description ""; }
            }
            description
                "TLV [70.3]: UsOfdmaSubcarrierCfg.SubcarrierUsage
                 non-defaults: [is_rcp_readonly: True]";
        }

    }  // g-UsOfdmaSubcarrierCfg grouping

}
