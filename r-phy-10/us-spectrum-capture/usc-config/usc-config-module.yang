module usc-config-module {
    yang-version 1;
    /* This file is automatically generated with Falcon V System's script.
       Any change made to this file will be lost. */

    namespace "falconvsystems:r-phy-10:usc-config-module";
    prefix "p-usc-config";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-UscConfig {
        tlv:id 4;
        description "TLV [41.4]: UsSpectrumCapture.UscConfig";
        leaf ScCfgTrigChannelType {
            tlv:id 1;
            tlv:repr uint8;
            type enumeration {
                enum OFDMA    { value  1; description ""; }
                enum SCQAM    { value  2; description ""; }
            }
            description
                "TLV [41.4.1]: UsSpectrumCapture.UscConfig.ScCfgTrigChannelType";
        }

        leaf ScCfgTrigChannelIndex {
            tlv:id 2;
            type uint8;
            description
                "TLV [41.4.2]: UsSpectrumCapture.UscConfig.ScCfgTrigChannelIndex";
        }

        leaf ScCfgTrigMode {
            tlv:id 3;
            tlv:repr uint8;
            type enumeration {
                enum other                { value  1; description ""; }
                enum freeRunning          { value  2; description ""; }
                enum miniSlotCount        { value  3; description ""; }
                enum sid                  { value  4; description ""; }
                enum quietProbeSymbol     { value  6; description ""; }
                enum burstIuc             { value  7; description ""; }
                enum timestamp            { value  8; description ""; }
                enum activeProbeSymbol    { value  9; description ""; }
            }
            description "TLV [41.4.3]: UsSpectrumCapture.UscConfig.ScCfgTrigMode";
        }

        leaf ScCfgTrigMinislotCount {
            tlv:id 4;
            type uint32;
            description
                "TLV [41.4.4]: UsSpectrumCapture.UscConfig.ScCfgTrigMinislotCount";
        }

        leaf ScCfgTrigSid {
            tlv:id 5;
            type uint16;
            description "TLV [41.4.5]: UsSpectrumCapture.UscConfig.ScCfgTrigSid";
        }

        leaf ScCfgTrigTimestamp {
            tlv:id 6;
            type uint64;
            description "TLV [41.4.6]: UsSpectrumCapture.UscConfig.ScCfgTrigTimestamp";
        }

        leaf ScCfgTrigIuc {
            tlv:id 7;
            tlv:repr uint8;
            type enumeration {
                enum other    { value  1; description ""; }
                enum iuc1     { value  2; description ""; }
                enum iuc2     { value  3; description ""; }
                enum iuc3     { value  4; description ""; }
                enum iuc4     { value  5; description ""; }
                enum iuc5     { value  6; description ""; }
                enum iuc6     { value  7; description ""; }
                enum iuc9     { value  8; description ""; }
                enum iuc10    { value  9; description ""; }
                enum iuc11    { value 10; description ""; }
                enum iuc12    { value 11; description ""; }
                enum iuc13    { value 12; description ""; }
            }
            description "TLV [41.4.7]: UsSpectrumCapture.UscConfig.ScCfgTrigIuc";
        }

        leaf ScCfgCenterFreq {
            tlv:id 8;
            type uint32;
            units "Hz";
            description "TLV [41.4.8]: UsSpectrumCapture.UscConfig.ScCfgCenterFreq";
        }

        leaf ScCfgSpan {
            tlv:id 9;
            type uint32;
            units "Hz";
            description "TLV [41.4.9]: UsSpectrumCapture.UscConfig.ScCfgSpan";
        }

        leaf ScCfgNumBins {
            tlv:id 10;
            type uint16;
            description "TLV [41.4.10]: UsSpectrumCapture.UscConfig.ScCfgNumBins";
        }

        leaf ScCfgAveraging {
            tlv:id 11;
            type uint8;
            description "TLV [41.4.11]: UsSpectrumCapture.UscConfig.ScCfgAveraging";
        }

        leaf ScCfgQualifyCenterFreq {
            tlv:id 12;
            type uint32;
            units "Hz";
            description
                "TLV [41.4.12]: UsSpectrumCapture.UscConfig.ScCfgQualifyCenterFreq";
        }

        leaf ScCfgQualifyBw {
            tlv:id 13;
            type uint32;
            units "Hz";
            description "TLV [41.4.13]: UsSpectrumCapture.UscConfig.ScCfgQualifyBw";
        }

        leaf ScCfgQualifyThreshold {
            tlv:id 14;
            type int8;
            units "dB";
            description
                "TLV [41.4.14]: UsSpectrumCapture.UscConfig.ScCfgQualifyThreshold";
        }

        leaf ScCfgWindow {
            tlv:id 15;
            tlv:repr uint8;
            type enumeration {
                enum other            { value  1; description ""; }
                enum rectangular      { value  2; description ""; }
                enum hann             { value  3; description ""; }
                enum blackmanHarris   { value  4; description ""; }
                enum hamming          { value  5; description ""; }
                enum flatTop          { value  6; description ""; }
                enum gaussian         { value  7; description ""; }
                enum chebyshev        { value  8; description ""; }
            }
            description "TLV [41.4.15]: UsSpectrumCapture.UscConfig.ScCfgWindow";
        }

        leaf ScCfgOutputFormat {
            tlv:id 16;
            tlv:repr uint8;
            type enumeration {
                enum timeIQ           { value  1; description ""; }
                enum fftPower         { value  2; description ""; }
                enum rawAdc           { value  3; description ""; }
                enum fftIQ            { value  4; description ""; }
                enum fftAmplitude     { value  5; description ""; }
                enum fftDb            { value  6; description ""; }
            }
            description "TLV [41.4.16]: UsSpectrumCapture.UscConfig.ScCfgOutputFormat";
        }

        leaf ScCfgRepeatPeriod {
            tlv:id 17;
            type uint32;
            units "microseconds";
            description "TLV [41.4.17]: UsSpectrumCapture.UscConfig.ScCfgRepeatPeriod";
        }

        leaf ScCfgRunDuration {
            tlv:id 18;
            type uint32;
            units "miliseconds";
            description "TLV [41.4.18]: UsSpectrumCapture.UscConfig.ScCfgRunDuration";
        }

        leaf ScCfgTriggerCount {
            tlv:id 19;
            type uint32;
            description "TLV [41.4.19]: UsSpectrumCapture.UscConfig.ScCfgTriggerCount";
        }

        leaf ScCfgAggregationMode {
            tlv:id 20;
            tlv:repr uint8;
            type enumeration {
                enum noAggregation    { value  0; description ""; }
                enum maxHold          { value  1; description ""; }
            }
            description
                "TLV [41.4.20]: UsSpectrumCapture.UscConfig.ScCfgAggregationMode";
        }

        leaf ScCfgAggregationPeriod {
            tlv:id 21;
            type uint32;
            units "microseconds";
            description
                "TLV [41.4.21]: UsSpectrumCapture.UscConfig.ScCfgAggregationPeriod";
        }

        leaf ScCfgPortStart {
            tlv:id 22;
            type uint8;
            description "TLV [41.4.22]: UsSpectrumCapture.UscConfig.ScCfgPortStart";
        }

        leaf ScCfgPortEnd {
            tlv:id 23;
            type uint8;
            description "TLV [41.4.23]: UsSpectrumCapture.UscConfig.ScCfgPortEnd";
        }

    }  // g-UscConfig grouping

}
