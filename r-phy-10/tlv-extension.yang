module tlv-extension {
    yang-version 1;
    /* This file is automatically generated with Falcon V System's script.
       Any change made to this file will be lost. */

    namespace "falconvsystems:r-phy-10:tlv-extension";
    prefix "tlv";

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    // T component
    extension id {
        argument "hierarchy_id";
        description
            "TYPE component of TLV codec.";
    }
    // L component
    // Note: should be evaluated in runtime for "Complex TLV" types
    extension len {
        argument "length";
        description
            "Optional - constant binary length for given TLV's value.";
    }
    // representation
    extension repr {
        argument "type";
        description
            "Binary representation of given leaf. To be skipped if is the same as in yang";
    }
    
}
