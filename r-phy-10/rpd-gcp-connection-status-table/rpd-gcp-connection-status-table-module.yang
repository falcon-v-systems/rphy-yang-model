module rpd-gcp-connection-status-table-module {
    yang-version 1;
    /* This file is automatically generated with Falcon V System's script.
       Any change made to this file will be lost. */

    namespace "falconvsystems:r-phy-10:rpd-gcp-connection-status-table-module";
    prefix "p-rpd-gcp-connection-status-table";

    // --- imports ---------------------------------------

    import ietf-yang-types {
        prefix "yang";
        description 
            "External YANG module.";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-RpdGcpConnectionStatusTable {
        tlv:id 105;
        description "TLV [105]: RpdGcpConnectionStatusTable";
        leaf Index {
            tlv:id 1;
            type uint8;
            description
                "TLV [105.1]: RpdGcpConnectionStatusTable.Index
                 non-defaults: [is_key: True]";
        }

        leaf CoreId {
            tlv:id 2;
            type yang:mac-address;
            description
                "TLV [105.2]: RpdGcpConnectionStatusTable.CoreId
                 non-defaults: [is_rcp_readonly: True, is_readonly: True]";
        }

        leaf RpdGcpConnectionStatus {
            tlv:id 3;
            tlv:repr uint8;
            type enumeration {
                enum Inactive         { value  1; description ""; }
                enum Connecting       { value  2; description ""; }
                enum Connected        { value  3; description ""; }
                enum ReConnecting     { value  4; description ""; }
            }
            description
                "TLV [105.3]: RpdGcpConnectionStatusTable.RpdGcpConnectionStatus
                 non-defaults: [is_rcp_readonly: True, is_readonly: True]";
        }

        leaf AuthenticationStatus {
            tlv:id 4;
            tlv:repr uint8;
            type enumeration {
                enum other                { value  0; description ""; }
                enum authenticated        { value  1; description ""; }
                enum authFailed           { value  2; description ""; }
                enum authNotPerformed     { value  3; description ""; }
            }
            description
                "TLV [105.4]: RpdGcpConnectionStatusTable.AuthenticationStatus
                 non-defaults: [is_rcp_readonly: True, is_readonly: True]";
        }

    }  // g-RpdGcpConnectionStatusTable grouping

}
