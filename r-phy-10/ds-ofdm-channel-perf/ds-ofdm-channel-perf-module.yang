module ds-ofdm-channel-perf-module {
    yang-version 1;
    /* This file is automatically generated with Falcon V System's script.
       Any change made to this file will be lost. */

    namespace "falconvsystems:r-phy-10:ds-ofdm-channel-perf-module";
    prefix "p-ds-ofdm-channel-perf";

    // --- imports ---------------------------------------

    import ds-ofdm-plc-perf-module {
        prefix "p-ds-ofdm-plc-perf";
        description 
            "File path: ds-ofdm-channel-perf/ds-ofdm-plc-perf/ds-ofdm-plc-perf-module.yang
            https://github.com/falcon-v-systems/rphy-yang-model/blob/master/r-phy-10/ds-ofdm-channel-perf/ds-ofdm-plc-perf/ds-ofdm-plc-perf-module.yang";
    }

    import ds-ofdm-profile-perf-module {
        prefix "p-ds-ofdm-profile-perf";
        description 
            "File path: ds-ofdm-channel-perf/ds-ofdm-profile-perf/ds-ofdm-profile-perf-module.yang
            https://github.com/falcon-v-systems/rphy-yang-model/blob/master/r-phy-10/ds-ofdm-channel-perf/ds-ofdm-profile-perf/ds-ofdm-profile-perf-module.yang";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-DsOfdmChannelPerf {
        tlv:id 73;
        description
            "TLV [73]: DsOfdmChannelPerf
             non-defaults: [is_rcp_readonly: True, is_readonly: True]";
        leaf Index {
            // no tlv:id given
            type uint16;
            description
                "TLV [73.X]: DsOfdmChannelPerf.Index
                 non-defaults: [is_key: True]";
        }

        leaf outDiscards {
            tlv:id 1;
            type uint64;
            units "packets";
            description
                "TLV [73.1]: DsOfdmChannelPerf.outDiscards
                 non-defaults: [is_rcp_readonly: True, is_readonly: True]";
        }

        leaf outErrors {
            tlv:id 2;
            type uint64;
            units "packets";
            description
                "TLV [73.2]: DsOfdmChannelPerf.outErrors
                 non-defaults: [is_rcp_readonly: True, is_readonly: True]";
        }

        container DsOfdmProfilePerf {
            tlv:id 3;
            description
                "TLV [73.3]: DsOfdmChannelPerf.DsOfdmProfilePerf
                 non-defaults: [is_rcp_readonly: True, is_readonly: True]";
            uses "p-ds-ofdm-profile-perf:g-DsOfdmProfilePerf";
        }

        leaf outPackets {
            tlv:id 4;
            type uint64;
            units "packets";
            description
                "TLV [73.4]: DsOfdmChannelPerf.outPackets
                 non-defaults: [is_rcp_readonly: True, is_readonly: True]";
        }

        leaf discontinuityTime {
            tlv:id 5;
            type binary;
            description
                "TLV [73.5]: DsOfdmChannelPerf.discontinuityTime
                 non-defaults: [is_rcp_readonly: True, is_readonly: True]";
        }

        container DsOfdmPlcPerf {
            tlv:id 6;
            description
                "TLV [73.6]: DsOfdmChannelPerf.DsOfdmPlcPerf
                 non-defaults: [is_rcp_readonly: True, is_readonly: True]";
            uses "p-ds-ofdm-plc-perf:g-DsOfdmPlcPerf";
        }

        leaf operStatusDsOfdm {
            tlv:id 7;
            tlv:repr uint8;
            type enumeration {
                enum up       { value  1; description ""; }
                enum down     { value  2; description ""; }
            }
            description
                "TLV [73.7]: DsOfdmChannelPerf.operStatusDsOfdm
                 non-defaults: [is_rcp_readonly: True, is_readonly: True]";
        }

        leaf PlcFrameTimeAlignment {
            tlv:id 8;
            type uint64;
            description
                "TLV [73.8]: DsOfdmChannelPerf.PlcFrameTimeAlignment
                 non-defaults: [is_rcp_readonly: True, is_readonly: True]";
        }

    }  // g-DsOfdmChannelPerf grouping

}
