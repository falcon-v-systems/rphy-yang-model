module rf-port-selector-module {
    yang-version 1;
    /* This file is automatically generated with Falcon V System's script.
       Any change made to this file will be lost. */

    namespace "falconvsystems:r-phy-10:rf-port-selector-module";
    prefix "p-rf-port-selector";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-RfPortSelector {
        tlv:id 13;
        description "TLV [13]: RfPortSelector";
        leaf RfPortIndex2 {
            tlv:id 1;
            type uint8;
            description "TLV [13.1]: RfPortSelector.RfPortIndex2";
        }

        leaf RfPortType {
            tlv:id 2;
            tlv:repr uint8;
            type enumeration {
                enum DsRfPort     { value  1; description ""; }
                enum UsRfPort     { value  2; description ""; }
            }
            description "TLV [13.2]: RfPortSelector.RfPortType";
        }

    }  // g-RfPortSelector grouping

}
