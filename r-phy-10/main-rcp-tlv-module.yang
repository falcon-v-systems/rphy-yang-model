module main-rcp-tlv-module {
    yang-version 1;
    /* This file is automatically generated with Falcon V System's script.
       Any change made to this file will be lost. */

    namespace "falconvsystems:r-phy-10:main-rcp-tlv-module";
    prefix "p-main-rcp-tlv";

    // --- imports ---------------------------------------

    import ira-module {
        prefix "p-ira";
        /*  File path: ira/ira-module.yang
            https://github.com/falcon-v-systems/rphy-yang-model/blob/master/r-phy-10/ira/ira-module.yang */
    }

    import ntf-module {
        prefix "p-ntf";
        /*  File path: ntf/ntf-module.yang
            https://github.com/falcon-v-systems/rphy-yang-model/blob/master/r-phy-10/ntf/ntf-module.yang */
    }

    import rex-module {
        prefix "p-rex";
        /*  File path: rex/rex-module.yang
            https://github.com/falcon-v-systems/rphy-yang-model/blob/master/r-phy-10/rex/rex-module.yang */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    container IRA {
        tlv:id 1;
        description "TLV [1]: IRA";
        uses "p-ira:g-IRA";
    }

    container REX {
        tlv:id 2;
        description "TLV [2]: REX";
        uses "p-rex:g-REX";
    }

    container NTF {
        tlv:id 3;
        description "TLV [3]: NTF";
        uses "p-ntf:g-NTF";
    }

}
