module log-ctrl-module {
    yang-version 1;
    /* This file is automatically generated with Falcon V System's script.
       Any change made to this file will be lost. */

    namespace "falconvsystems:r-phy-10:log-ctrl-module";
    prefix "p-log-ctrl";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-LogCtrl {
        tlv:id 2;
        description "TLV [40.2]: RpdCtrl.LogCtrl";
        leaf ResetLog {
            tlv:id 1;
            tlv:repr uint8;
            type enumeration {
                enum localEventLog        { value  0; description ""; }
                enum eventPendingQueue    { value  1; description ""; }
            }
            description "TLV [40.2.1]: RpdCtrl.LogCtrl.ResetLog";
        }

    }  // g-LogCtrl grouping

}
