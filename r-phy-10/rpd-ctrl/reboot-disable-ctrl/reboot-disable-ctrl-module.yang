module reboot-disable-ctrl-module {
    yang-version 1;
    /* This file is automatically generated with Falcon V System's script.
       Any change made to this file will be lost. */

    namespace "falconvsystems:r-phy-10:reboot-disable-ctrl-module";
    prefix "p-reboot-disable-ctrl";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-RebootDisableCtrl {
        tlv:id 5;
        description "TLV [40.5]: RpdCtrl.RebootDisableCtrl";
        leaf RebootDisable {
            tlv:id 1;
            type boolean;
            description "TLV [40.5.1]: RpdCtrl.RebootDisableCtrl.RebootDisable";
        }

        leaf DisableTimeout {
            tlv:id 2;
            type uint32;
            units "seconds";
            description "TLV [40.5.2]: RpdCtrl.RebootDisableCtrl.DisableTimeout";
        }

    }  // g-RebootDisableCtrl grouping

}
