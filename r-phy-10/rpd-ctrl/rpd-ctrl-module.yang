module rpd-ctrl-module {
    yang-version 1;
    /* This file is automatically generated with Falcon V System's script.
       Any change made to this file will be lost. */

    namespace "falconvsystems:r-phy-10:rpd-ctrl-module";
    prefix "p-rpd-ctrl";

    // --- imports ---------------------------------------

    import crash-data-file-ctrl-module {
        prefix "p-crash-data-file-ctrl";
        description 
            "File path: rpd-ctrl/crash-data-file-ctrl/crash-data-file-ctrl-module.yang
            https://github.com/falcon-v-systems/rphy-yang-model/blob/master/r-phy-10/rpd-ctrl/crash-data-file-ctrl/crash-data-file-ctrl-module.yang";
    }

    import crash-data-server-ctrl-module {
        prefix "p-crash-data-server-ctrl";
        description 
            "File path: rpd-ctrl/crash-data-server-ctrl/crash-data-server-ctrl-module.yang
            https://github.com/falcon-v-systems/rphy-yang-model/blob/master/r-phy-10/rpd-ctrl/crash-data-server-ctrl/crash-data-server-ctrl-module.yang";
    }

    import log-ctrl-module {
        prefix "p-log-ctrl";
        description 
            "File path: rpd-ctrl/log-ctrl/log-ctrl-module.yang
            https://github.com/falcon-v-systems/rphy-yang-model/blob/master/r-phy-10/rpd-ctrl/log-ctrl/log-ctrl-module.yang";
    }

    import reboot-disable-ctrl-module {
        prefix "p-reboot-disable-ctrl";
        description 
            "File path: rpd-ctrl/reboot-disable-ctrl/reboot-disable-ctrl-module.yang
            https://github.com/falcon-v-systems/rphy-yang-model/blob/master/r-phy-10/rpd-ctrl/reboot-disable-ctrl/reboot-disable-ctrl-module.yang";
    }

    import reset-ctrl-module {
        prefix "p-reset-ctrl";
        description 
            "File path: rpd-ctrl/reset-ctrl/reset-ctrl-module.yang
            https://github.com/falcon-v-systems/rphy-yang-model/blob/master/r-phy-10/rpd-ctrl/reset-ctrl/reset-ctrl-module.yang";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-RpdCtrl {
        tlv:id 40;
        description "TLV [40]: RpdCtrl";
        container ResetCtrl {
            tlv:id 1;
            description "TLV [40.1]: RpdCtrl.ResetCtrl";
            uses "p-reset-ctrl:g-ResetCtrl";
        }

        container LogCtrl {
            tlv:id 2;
            description "TLV [40.2]: RpdCtrl.LogCtrl";
            uses "p-log-ctrl:g-LogCtrl";
        }

        container CrashDataFileCtrl {
            tlv:id 3;
            description "TLV [40.3]: RpdCtrl.CrashDataFileCtrl";
            uses "p-crash-data-file-ctrl:g-CrashDataFileCtrl";
        }

        container CrashDataServerCtrl {
            tlv:id 4;
            description "TLV [40.4]: RpdCtrl.CrashDataServerCtrl";
            uses "p-crash-data-server-ctrl:g-CrashDataServerCtrl";
        }

        container RebootDisableCtrl {
            tlv:id 5;
            description "TLV [40.5]: RpdCtrl.RebootDisableCtrl";
            uses "p-reboot-disable-ctrl:g-RebootDisableCtrl";
        }

    }  // g-RpdCtrl grouping

}
