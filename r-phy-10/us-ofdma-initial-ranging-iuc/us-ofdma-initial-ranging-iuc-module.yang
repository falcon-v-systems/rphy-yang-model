module us-ofdma-initial-ranging-iuc-module {
    yang-version 1;
    /* This file is automatically generated with Falcon V System's script.
       Any change made to this file will be lost. */

    namespace "falconvsystems:r-phy-10:us-ofdma-initial-ranging-iuc-module";
    prefix "p-us-ofdma-initial-ranging-iuc";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-UsOfdmaInitialRangingIuc {
        tlv:id 67;
        description "TLV [67]: UsOfdmaInitialRangingIuc";
        leaf NumSubcarriers {
            tlv:id 1;
            type uint16;
            description
                "TLV [67.1]: UsOfdmaInitialRangingIuc.NumSubcarriers
                 non-defaults: [is_rcp_readonly: True]";
        }

        leaf Guardband {
            tlv:id 2;
            type uint16;
            description
                "TLV [67.2]: UsOfdmaInitialRangingIuc.Guardband
                 non-defaults: [is_rcp_readonly: True]";
        }

    }  // g-UsOfdmaInitialRangingIuc grouping

}
