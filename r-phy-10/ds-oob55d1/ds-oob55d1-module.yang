module ds-oob55d1-module {
    yang-version 1;
    /* This file is automatically generated with Falcon V System's script.
       Any change made to this file will be lost. */

    namespace "falconvsystems:r-phy-10:ds-oob55d1-module";
    prefix "p-ds-oob55d1";

    // --- imports ---------------------------------------

    import ietf-yang-types {
        prefix "yang";
        description 
            "External YANG module.";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-DsOob55d1 {
        tlv:id 91;
        description "TLV [91]: DsOob55d1";
        leaf AdminState {
            tlv:id 1;
            tlv:repr uint8;
            type enumeration {
                enum other    { value  1; description ""; }
                enum up       { value  2; description ""; }
                enum down     { value  3; description ""; }
                enum testing  { value  4; description ""; }
            }
            description "TLV [91.1]: DsOob55d1.AdminState";
        }

        leaf CcapCoreOwner {
            tlv:id 2;
            type yang:mac-address;
            description "TLV [91.2]: DsOob55d1.CcapCoreOwner";
        }

        leaf RfMute {
            tlv:id 3;
            type boolean;
            description "TLV [91.3]: DsOob55d1.RfMute";
        }

        leaf Frequency {
            tlv:id 4;
            type uint32;
            units "Hz";
            description "TLV [91.4]: DsOob55d1.Frequency";
        }

        leaf PowerAdjust {
            tlv:id 5;
            type int16;
            units "TenthdB";
            description "TLV [91.5]: DsOob55d1.PowerAdjust";
        }

        leaf SecondFrequency {
            tlv:id 6;
            type uint32;
            units "Hz";
            description "TLV [91.6]: DsOob55d1.SecondFrequency";
        }

        leaf SfPowerAdjust {
            tlv:id 7;
            type int16;
            units "TenthdB";
            description "TLV [91.7]: DsOob55d1.SfPowerAdjust";
        }

        leaf SfAdminState {
            tlv:id 8;
            tlv:repr uint8;
            type enumeration {
                enum other    { value  1; description ""; }
                enum up       { value  2; description ""; }
                enum down     { value  3; description ""; }
                enum testing  { value  4; description ""; }
            }
            description "TLV [91.8]: DsOob55d1.SfAdminState";
        }

        leaf SfRfMute {
            tlv:id 9;
            type boolean;
            description "TLV [91.9]: DsOob55d1.SfRfMute";
        }

    }  // g-DsOob55d1 grouping

}
