module bw-req-aggr-control-ofdma-module {
    yang-version 1;
    /* This file is automatically generated with Falcon V System's script.
       Any change made to this file will be lost. */

    namespace "falconvsystems:r-phy-10:bw-req-aggr-control-ofdma-module";
    prefix "p-bw-req-aggr-control-ofdma";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-BwReqAggrControlOfdma {
        tlv:id 17;
        description "TLV [66.17]: UsOfdmaChannelConfig.BwReqAggrControlOfdma";
        leaf MaxReqBlockEnqTimeout {
            tlv:id 1;
            type uint16;
            units "microseconds";
            description
                "TLV [66.17.1]: UsOfdmaChannelConfig.BwReqAggrControlOfdma.MaxReqBlockEnqTimeout";
        }

        leaf MaxReqBlockEnqNumber {
            tlv:id 2;
            type uint8;
            description
                "TLV [66.17.2]: UsOfdmaChannelConfig.BwReqAggrControlOfdma.MaxReqBlockEnqNumber";
        }

    }  // g-BwReqAggrControlOfdma grouping

}
