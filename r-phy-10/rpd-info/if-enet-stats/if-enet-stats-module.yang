module if-enet-stats-module {
    yang-version 1;
    /* This file is automatically generated with Falcon V System's script.
       Any change made to this file will be lost. */

    namespace "falconvsystems:r-phy-10:if-enet-stats-module";
    prefix "p-if-enet-stats";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-IfEnetStats {
        tlv:id 9;
        description "TLV [100.9]: RpdInfo.IfEnetStats";
        leaf EnetPortIndex {
            tlv:id 1;
            type uint8;
            description
                "TLV [100.9.1]: RpdInfo.IfEnetStats.EnetPortIndex
                 non-defaults: [is_key: True]";
        }

        leaf InOctets {
            tlv:id 2;
            type uint64;
            description "TLV [100.9.2]: RpdInfo.IfEnetStats.InOctets";
        }

        leaf InUnicastOctets {
            tlv:id 3;
            type uint64;
            description "TLV [100.9.3]: RpdInfo.IfEnetStats.InUnicastOctets";
        }

        leaf InMulticastOctets {
            tlv:id 4;
            type uint64;
            description "TLV [100.9.4]: RpdInfo.IfEnetStats.InMulticastOctets";
        }

        leaf InBroadcastOctets {
            tlv:id 5;
            type uint64;
            description "TLV [100.9.5]: RpdInfo.IfEnetStats.InBroadcastOctets";
        }

        leaf InFrames {
            tlv:id 6;
            type uint64;
            description "TLV [100.9.6]: RpdInfo.IfEnetStats.InFrames";
        }

        leaf InUnicastFrames {
            tlv:id 7;
            type uint64;
            description "TLV [100.9.7]: RpdInfo.IfEnetStats.InUnicastFrames";
        }

        leaf InMulticastFrames {
            tlv:id 8;
            type uint64;
            description "TLV [100.9.8]: RpdInfo.IfEnetStats.InMulticastFrames";
        }

        leaf InBroadcastFrames {
            tlv:id 9;
            type uint64;
            description "TLV [100.9.9]: RpdInfo.IfEnetStats.InBroadcastFrames";
        }

        leaf InDiscards {
            tlv:id 10;
            type uint64;
            description "TLV [100.9.10]: RpdInfo.IfEnetStats.InDiscards";
        }

        leaf InErrors {
            tlv:id 11;
            type uint64;
            description "TLV [100.9.11]: RpdInfo.IfEnetStats.InErrors";
        }

        leaf InUnknownProtos {
            tlv:id 12;
            type uint64;
            description "TLV [100.9.12]: RpdInfo.IfEnetStats.InUnknownProtos";
        }

        leaf OutOctets {
            tlv:id 13;
            type uint64;
            description "TLV [100.9.13]: RpdInfo.IfEnetStats.OutOctets";
        }

        leaf OutFrames {
            tlv:id 17;
            type uint64;
            description "TLV [100.9.17]: RpdInfo.IfEnetStats.OutFrames";
        }

        leaf OutUnicastFrames {
            tlv:id 18;
            type uint64;
            description "TLV [100.9.18]: RpdInfo.IfEnetStats.OutUnicastFrames";
        }

        leaf OutMulticastFrames {
            tlv:id 19;
            type uint64;
            description "TLV [100.9.19]: RpdInfo.IfEnetStats.OutMulticastFrames";
        }

        leaf OutBroadcastFrames {
            tlv:id 20;
            type uint64;
            description "TLV [100.9.20]: RpdInfo.IfEnetStats.OutBroadcastFrames";
        }

        leaf OutDiscards {
            tlv:id 21;
            type uint64;
            description "TLV [100.9.21]: RpdInfo.IfEnetStats.OutDiscards";
        }

        leaf OutErrors {
            tlv:id 22;
            type uint64;
            description "TLV [100.9.22]: RpdInfo.IfEnetStats.OutErrors";
        }

        leaf CounterDiscontinuityTime {
            tlv:id 23;
            type binary;
            description "TLV [100.9.23]: RpdInfo.IfEnetStats.CounterDiscontinuityTime";
        }

    }  // g-IfEnetStats grouping

}
