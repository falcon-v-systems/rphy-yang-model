module trust-anchor-cert-module {
    yang-version 1;
    /* This file is automatically generated with Falcon V System's script.
       Any change made to this file will be lost. */

    namespace "falconvsystems:r-phy-10:trust-anchor-cert-module";
    prefix "p-trust-anchor-cert";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-TrustAnchorCert {
        tlv:id 27;
        description "TLV [100.27]: RpdInfo.TrustAnchorCert";
        leaf Index {
            tlv:id 1;
            type uint32;
            description
                "TLV [100.27.1]: RpdInfo.TrustAnchorCert.Index
                 non-defaults: [is_key: True]";
        }

        leaf CaCert {
            tlv:id 2;
            type binary;
            description "TLV [100.27.2]: RpdInfo.TrustAnchorCert.CaCert";
        }

    }  // g-TrustAnchorCert grouping

}
