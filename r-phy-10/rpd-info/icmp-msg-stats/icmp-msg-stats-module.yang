module icmp-msg-stats-module {
    yang-version 1;
    /* This file is automatically generated with Falcon V System's script.
       Any change made to this file will be lost. */

    namespace "falconvsystems:r-phy-10:icmp-msg-stats-module";
    prefix "p-icmp-msg-stats";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-IcmpMsgStats {
        tlv:id 19;
        description "TLV [100.19]: RpdInfo.IcmpMsgStats";
        leaf IpVersion {
            tlv:id 1;
            type uint8;
            description
                "TLV [100.19.1]: RpdInfo.IcmpMsgStats.IpVersion
                 non-defaults: [is_key: True]";
        }

        leaf Type {
            tlv:id 2;
            type uint8;
            description
                "TLV [100.19.2]: RpdInfo.IcmpMsgStats.Type
                 non-defaults: [is_key: True]";
        }

        leaf InPkts {
            tlv:id 3;
            type uint64;
            description "TLV [100.19.3]: RpdInfo.IcmpMsgStats.InPkts";
        }

        leaf OutPkts {
            tlv:id 4;
            type uint64;
            description "TLV [100.19.4]: RpdInfo.IcmpMsgStats.OutPkts";
        }

    }  // g-IcmpMsgStats grouping

}
