module ip-net-to-physical-module {
    yang-version 1;
    /* This file is automatically generated with Falcon V System's script.
       Any change made to this file will be lost. */

    namespace "falconvsystems:r-phy-10:ip-net-to-physical-module";
    prefix "p-ip-net-to-physical";

    // --- imports ---------------------------------------

    import ietf-inet-types {
        prefix "inet";
        description 
            "External YANG module.";
    }

    import ietf-yang-types {
        prefix "yang";
        description 
            "External YANG module.";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-IpNetToPhysical {
        tlv:id 16;
        description "TLV [100.16]: RpdInfo.IpNetToPhysical";
        leaf EnetPortIndex {
            tlv:id 1;
            type uint8;
            description
                "TLV [100.16.1]: RpdInfo.IpNetToPhysical.EnetPortIndex
                 non-defaults: [is_key: True]";
        }

        leaf AddrType {
            tlv:id 2;
            tlv:repr int32;
            type enumeration {
                enum unknown  { value  0; description ""; }
                enum ipv4     { value  1; description ""; }
                enum ipv6     { value  2; description ""; }
                enum ipv4z    { value  3; description ""; }
                enum ipv6z    { value  4; description ""; }
                enum dns      { value 16; description ""; }
            }
            description
                "TLV [100.16.2]: RpdInfo.IpNetToPhysical.AddrType
                 non-defaults: [is_key: True]";
        }

        leaf IpAddress {
            tlv:id 3;
            type inet:ip-address;
            description
                "TLV [100.16.3]: RpdInfo.IpNetToPhysical.IpAddress
                 non-defaults: [is_key: True]";
        }

        leaf PhysAddress {
            tlv:id 4;
            type yang:mac-address;
            description "TLV [100.16.4]: RpdInfo.IpNetToPhysical.PhysAddress";
        }

        leaf LastUpdated {
            tlv:id 5;
            type uint32;
            description "TLV [100.16.5]: RpdInfo.IpNetToPhysical.LastUpdated";
        }

        leaf Type {
            tlv:id 6;
            tlv:repr uint8;
            type enumeration {
                enum other    { value  1; description ""; }
                enum invalid  { value  2; description ""; }
                enum dynamic  { value  3; description ""; }
                enum static   { value  4; description ""; }
                enum local    { value  5; description ""; }
            }
            description "TLV [100.16.6]: RpdInfo.IpNetToPhysical.Type";
        }

        leaf State {
            tlv:id 7;
            tlv:repr uint8;
            type enumeration {
                enum reachable    { value  1; description ""; }
                enum stale        { value  2; description ""; }
                enum delay        { value  3; description ""; }
                enum probe        { value  4; description ""; }
                enum invalid      { value  5; description ""; }
                enum unknown      { value  6; description ""; }
                enum incomplete   { value  7; description ""; }
            }
            description "TLV [100.16.7]: RpdInfo.IpNetToPhysical.State";
        }

    }  // g-IpNetToPhysical grouping

}
