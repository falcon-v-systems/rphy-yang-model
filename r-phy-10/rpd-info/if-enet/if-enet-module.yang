module if-enet-module {
    yang-version 1;
    /* This file is automatically generated with Falcon V System's script.
       Any change made to this file will be lost. */

    namespace "falconvsystems:r-phy-10:if-enet-module";
    prefix "p-if-enet";

    // --- imports ---------------------------------------

    import ietf-yang-types {
        prefix "yang";
        description 
            "External YANG module.";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-IfEnet {
        tlv:id 8;
        description "TLV [100.8]: RpdInfo.IfEnet";
        leaf EnetPortIndex {
            tlv:id 1;
            type uint8;
            description
                "TLV [100.8.1]: RpdInfo.IfEnet.EnetPortIndex
                 non-defaults: [is_key: True]";
        }

        leaf Name {
            tlv:id 2;
            type string;
            description "TLV [100.8.2]: RpdInfo.IfEnet.Name";
        }

        leaf Descr {
            tlv:id 3;
            type string;
            description "TLV [100.8.3]: RpdInfo.IfEnet.Descr";
        }

        leaf Type {
            tlv:id 4;
            type uint16;
            description "TLV [100.8.4]: RpdInfo.IfEnet.Type";
        }

        leaf Alias {
            tlv:id 5;
            type string;
            description "TLV [100.8.5]: RpdInfo.IfEnet.Alias";
        }

        leaf Mtu {
            tlv:id 6;
            type int32;
            description "TLV [100.8.6]: RpdInfo.IfEnet.Mtu";
        }

        leaf PhysAddress {
            tlv:id 7;
            type yang:mac-address;
            description "TLV [100.8.7]: RpdInfo.IfEnet.PhysAddress";
        }

        leaf AdminStatus {
            tlv:id 8;
            tlv:repr uint8;
            type enumeration {
                enum up       { value  1; description ""; }
                enum down     { value  2; description ""; }
                enum testing  { value  3; description ""; }
            }
            description "TLV [100.8.8]: RpdInfo.IfEnet.AdminStatus";
        }

        leaf OperStatus {
            tlv:id 9;
            tlv:repr uint8;
            type enumeration {
                enum up               { value  1; description ""; }
                enum down             { value  2; description ""; }
                enum testing          { value  3; description ""; }
                enum unknown          { value  4; description ""; }
                enum dormant          { value  5; description ""; }
                enum notPresent       { value  6; description ""; }
                enum lowerLayerDown   { value  7; description ""; }
            }
            description "TLV [100.8.9]: RpdInfo.IfEnet.OperStatus";
        }

        leaf LastChange {
            tlv:id 10;
            type uint32;
            description "TLV [100.8.10]: RpdInfo.IfEnet.LastChange";
        }

        leaf HighSpeed {
            tlv:id 11;
            type uint32;
            description "TLV [100.8.11]: RpdInfo.IfEnet.HighSpeed";
        }

        leaf LinkUpDownTrapEnable {
            tlv:id 12;
            type boolean;
            description "TLV [100.8.12]: RpdInfo.IfEnet.LinkUpDownTrapEnable";
        }

        leaf PromiscuousMode {
            tlv:id 13;
            type boolean;
            description "TLV [100.8.13]: RpdInfo.IfEnet.PromiscuousMode";
        }

        leaf ConnectorPresent {
            tlv:id 14;
            type boolean;
            description "TLV [100.8.14]: RpdInfo.IfEnet.ConnectorPresent";
        }

    }  // g-IfEnet grouping

}
