module sfp-plus-status-module {
    yang-version 1;
    /* This file is automatically generated with Falcon V System's script.
       Any change made to this file will be lost. */

    namespace "falconvsystems:r-phy-10:sfp-plus-status-module";
    prefix "p-sfp-plus-status";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-SfpPlusStatus {
        tlv:id 18;
        description "TLV [100.18]: RpdInfo.SfpPlusStatus";
        leaf EnetPortIndex {
            tlv:id 1;
            type uint8;
            description
                "TLV [100.18.1]: RpdInfo.SfpPlusStatus.EnetPortIndex
                 non-defaults: [is_key: True]";
        }

        leaf Status {
            tlv:id 2;
            tlv:repr uint16;
            type enumeration {
                enum unknown          { value  0; description ""; }
                enum notInstalled     { value  1; description ""; }
                enum installed        { value  2; description ""; }
                enum faulty           { value  3; description ""; }
                enum operational      { value  4; description ""; }
                enum enabled          { value  5; description ""; }
                enum disabled         { value  6; description ""; }
                enum invalidCcBase    { value  7; description ""; }
                enum invalidCcExt     { value  8; description ""; }
            }
            description "TLV [100.18.2]: RpdInfo.SfpPlusStatus.Status";
        }

        leaf Identifier {
            tlv:id 3;
            tlv:repr uint8;
            type enumeration {
                enum unknown          { value  0; description ""; }
                enum gbic             { value  1; description ""; }
                enum sff              { value  2; description ""; }
                enum sfpOrSfpPlus     { value  3; description ""; }
                enum xbi              { value  4; description ""; }
                enum xenpack          { value  5; description ""; }
                enum xfp              { value  6; description ""; }
                enum xff              { value  7; description ""; }
                enum xfpE             { value  8; description ""; }
                enum xPak             { value  9; description ""; }
                enum x2               { value 10; description ""; }
                enum dwdmSfp          { value 11; description ""; }
                enum qsfp             { value 12; description ""; }
            }
            description "TLV [100.18.3]: RpdInfo.SfpPlusStatus.Identifier";
        }

        leaf ExtendedIdentifier {
            tlv:id 4;
            type uint8;
            description "TLV [100.18.4]: RpdInfo.SfpPlusStatus.ExtendedIdentifier";
        }

        leaf ConnectorType {
            tlv:id 5;
            tlv:repr uint8;
            type enumeration {
                enum unknown          { value  0; description ""; }
                enum sc               { value  1; description ""; }
                enum fcscc1           { value  2; description ""; }
                enum fcscc2           { value  3; description ""; }
                enum bnctnc           { value  4; description ""; }
                enum fcch             { value  5; description ""; }
                enum fiberJack        { value  6; description ""; }
                enum lc               { value  7; description ""; }
                enum mtrj             { value  8; description ""; }
                enum mu               { value  9; description ""; }
                enum sg               { value 10; description ""; }
                enum opticalPigtail   { value 11; description ""; }
                enum mpoParallel      { value 12; description ""; }
                enum hssdc2           { value 32; description ""; }
                enum copperPigtail    { value 33; description ""; }
                enum rj45             { value 34; description ""; }
            }
            description "TLV [100.18.5]: RpdInfo.SfpPlusStatus.ConnectorType";
        }

        leaf TransceiverComplianceCodes {
            tlv:id 6;
            type binary;
            description
                "TLV [100.18.6]: RpdInfo.SfpPlusStatus.TransceiverComplianceCodes";
        }

        leaf TransceiverComplianceCode36 {
            tlv:id 7;
            type uint8;
            description
                "TLV [100.18.7]: RpdInfo.SfpPlusStatus.TransceiverComplianceCode36";
        }

        leaf Encoding {
            tlv:id 8;
            tlv:repr uint8;
            type enumeration {
                enum unspecified          { value  0; description ""; }
                enum eightTenB            { value  1; description ""; }
                enum fourFiveB            { value  2; description ""; }
                enum nrz                  { value  3; description ""; }
                enum manchester           { value  4; description ""; }
                enum sonetScrambled       { value  5; description ""; }
                enum sixtyFourSixtySixB   { value  6; description ""; }
            }
            description "TLV [100.18.8]: RpdInfo.SfpPlusStatus.Encoding";
        }

        leaf BitRateNominal {
            tlv:id 9;
            type uint8;
            description "TLV [100.18.9]: RpdInfo.SfpPlusStatus.BitRateNominal";
        }

        leaf RateIdentifier {
            tlv:id 10;
            tlv:repr uint16;
            type enumeration {
                enum unspecified          { value  0; description ""; }
                enum sff8079              { value  1; description ""; }
                enum sff8431Rx            { value  2; description ""; }
                enum unspecified3         { value  3; description ""; }
                enum sff8431Tx            { value  4; description ""; }
                enum unspecified5         { value  5; description ""; }
                enum sff8431indepRxTx     { value  6; description ""; }
                enum unspecified7         { value  7; description ""; }
                enum fcpi5Rx              { value  8; description ""; }
                enum unspecified9         { value  9; description ""; }
                enum fcpi5Tx              { value 10; description ""; }
            }
            description "TLV [100.18.10]: RpdInfo.SfpPlusStatus.RateIdentifier";
        }

        leaf LengthKm {
            tlv:id 11;
            type uint8;
            description "TLV [100.18.11]: RpdInfo.SfpPlusStatus.LengthKm";
        }

        leaf Length100M {
            tlv:id 12;
            type uint8;
            description "TLV [100.18.12]: RpdInfo.SfpPlusStatus.Length100M";
        }

        leaf Length50Mi10M {
            tlv:id 13;
            type uint8;
            description "TLV [100.18.13]: RpdInfo.SfpPlusStatus.Length50Mi10M";
        }

        leaf Length62Pt5Mi10M {
            tlv:id 14;
            type uint8;
            description "TLV [100.18.14]: RpdInfo.SfpPlusStatus.Length62Pt5Mi10M";
        }

        leaf LengthCopperM {
            tlv:id 15;
            type uint8;
            description "TLV [100.18.15]: RpdInfo.SfpPlusStatus.LengthCopperM";
        }

        leaf Length50MiOm3 {
            tlv:id 16;
            type uint8;
            description "TLV [100.18.16]: RpdInfo.SfpPlusStatus.Length50MiOm3";
        }

        leaf VendorName {
            tlv:id 17;
            type string;
            description "TLV [100.18.17]: RpdInfo.SfpPlusStatus.VendorName";
        }

        leaf VendorOui {
            tlv:id 18;
            type binary;
            description "TLV [100.18.18]: RpdInfo.SfpPlusStatus.VendorOui";
        }

        leaf VendorPartNum {
            tlv:id 19;
            type string;
            description "TLV [100.18.19]: RpdInfo.SfpPlusStatus.VendorPartNum";
        }

        leaf VendorSerialNum {
            tlv:id 20;
            type string;
            description "TLV [100.18.20]: RpdInfo.SfpPlusStatus.VendorSerialNum";
        }

        leaf VendorRev {
            tlv:id 21;
            type string;
            description "TLV [100.18.21]: RpdInfo.SfpPlusStatus.VendorRev";
        }

        leaf LaserWavelength {
            tlv:id 22;
            type uint16;
            description "TLV [100.18.22]: RpdInfo.SfpPlusStatus.LaserWavelength";
        }

        leaf Options {
            tlv:id 23;
            tlv:repr uint16;
            type enumeration {
                enum unallocated0         { value  0; description ""; }
                enum rxlosNormal          { value  1; description ""; }
                enum rxlosInverted        { value  2; description ""; }
                enum txFault              { value  3; description ""; }
                enum txDisable            { value  4; description ""; }
                enum rateSelect           { value  5; description ""; }
                enum unallocated6         { value  6; description ""; }
                enum unallocated7         { value  7; description ""; }
                enum linearOutput         { value  8; description ""; }
                enum powerLevel           { value  9; description ""; }
                enum cooledTransceiver    { value 10; description ""; }
            }
            description "TLV [100.18.23]: RpdInfo.SfpPlusStatus.Options";
        }

        leaf BitRateMax {
            tlv:id 24;
            type uint8;
            description "TLV [100.18.24]: RpdInfo.SfpPlusStatus.BitRateMax";
        }

        leaf BitRateMin {
            tlv:id 25;
            type uint8;
            description "TLV [100.18.25]: RpdInfo.SfpPlusStatus.BitRateMin";
        }

        leaf VendorDate {
            tlv:id 26;
            type string;
            description "TLV [100.18.26]: RpdInfo.SfpPlusStatus.VendorDate";
        }

        leaf VendorSpecificLotCode {
            tlv:id 27;
            type string;
            description "TLV [100.18.27]: RpdInfo.SfpPlusStatus.VendorSpecificLotCode";
        }

        leaf DiagMonitorType {
            tlv:id 28;
            tlv:repr uint8;
            type enumeration {
                enum unallocated0         { value  0; description ""; }
                enum unallocated1         { value  1; description ""; }
                enum addrChangeReq        { value  2; description ""; }
                enum recPwrMeasType       { value  3; description ""; }
                enum externCalibrated     { value  4; description ""; }
                enum internCalibrated     { value  5; description ""; }
                enum digDiagImpl          { value  6; description ""; }
                enum legacyImpl           { value  7; description ""; }
            }
            description "TLV [100.18.28]: RpdInfo.SfpPlusStatus.DiagMonitorType";
        }

        leaf EnhancedOptions {
            tlv:id 29;
            tlv:repr uint8;
            type enumeration {
                enum unknown              { value  0; description ""; }
                enum rateCtrlImpl         { value  1; description ""; }
                enum appSelCtrlImpl       { value  2; description ""; }
                enum rateSelectCtrlImpl   { value  3; description ""; }
                enum rxLosMonImpl         { value  4; description ""; }
                enum txFaultMonImpl       { value  5; description ""; }
                enum txDisableMonImpl     { value  6; description ""; }
                enum allAlarmsImpl        { value  7; description ""; }
            }
            description "TLV [100.18.29]: RpdInfo.SfpPlusStatus.EnhancedOptions";
        }

        leaf Sff8472Compliance {
            tlv:id 30;
            type uint8;
            description "TLV [100.18.30]: RpdInfo.SfpPlusStatus.Sff8472Compliance";
        }

        leaf VendorSpecificData {
            tlv:id 31;
            type binary;
            description "TLV [100.18.31]: RpdInfo.SfpPlusStatus.VendorSpecificData";
        }

        leaf MeasuredTxOutputPwr {
            tlv:id 32;
            type uint16;
            description "TLV [100.18.32]: RpdInfo.SfpPlusStatus.MeasuredTxOutputPwr";
        }

        leaf MeasuredRxInputPwr {
            tlv:id 33;
            type uint16;
            description "TLV [100.18.33]: RpdInfo.SfpPlusStatus.MeasuredRxInputPwr";
        }

        leaf DigitalDiagA2Info {
            tlv:id 34;
            type binary;
            description "TLV [100.18.34]: RpdInfo.SfpPlusStatus.DigitalDiagA2Info";
        }

    }  // g-SfpPlusStatus grouping

}
