module ip-default-router-module {
    yang-version 1;
    /* This file is automatically generated with Falcon V System's script.
       Any change made to this file will be lost. */

    namespace "falconvsystems:r-phy-10:ip-default-router-module";
    prefix "p-ip-default-router";

    // --- imports ---------------------------------------

    import ietf-inet-types {
        prefix "inet";
        description 
            "External YANG module.";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-IpDefaultRouter {
        tlv:id 17;
        description "TLV [100.17]: RpdInfo.IpDefaultRouter";
        leaf AddrType {
            tlv:id 1;
            tlv:repr int32;
            type enumeration {
                enum unknown  { value  0; description ""; }
                enum ipv4     { value  1; description ""; }
                enum ipv6     { value  2; description ""; }
                enum ipv4z    { value  3; description ""; }
                enum ipv6z    { value  4; description ""; }
                enum dns      { value 16; description ""; }
            }
            description
                "TLV [100.17.1]: RpdInfo.IpDefaultRouter.AddrType
                 non-defaults: [is_key: True]";
        }

        leaf IpAddress {
            tlv:id 2;
            type inet:ip-address;
            description
                "TLV [100.17.2]: RpdInfo.IpDefaultRouter.IpAddress
                 non-defaults: [is_key: True]";
        }

        leaf EnetPortIndex {
            tlv:id 3;
            type uint8;
            description
                "TLV [100.17.3]: RpdInfo.IpDefaultRouter.EnetPortIndex
                 non-defaults: [is_key: True]";
        }

        leaf Lifetime {
            tlv:id 4;
            type uint16;
            description "TLV [100.17.4]: RpdInfo.IpDefaultRouter.Lifetime";
        }

        leaf Preference {
            tlv:id 5;
            tlv:repr int8;
            type enumeration {
                enum reserved     { value -2; description ""; }
                enum low          { value -1; description ""; }
                enum medium       { value  0; description ""; }
                enum high         { value  1; description ""; }
            }
            description "TLV [100.17.5]: RpdInfo.IpDefaultRouter.Preference";
        }

    }  // g-IpDefaultRouter grouping

}
