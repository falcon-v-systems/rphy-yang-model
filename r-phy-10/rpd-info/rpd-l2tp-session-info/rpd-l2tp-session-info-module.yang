module rpd-l2tp-session-info-module {
    yang-version 1;
    /* This file is automatically generated with Falcon V System's script.
       Any change made to this file will be lost. */

    namespace "falconvsystems:r-phy-10:rpd-l2tp-session-info-module";
    prefix "p-rpd-l2tp-session-info";

    // --- imports ---------------------------------------

    import ietf-inet-types {
        prefix "inet";
        description 
            "External YANG module.";
    }

    import ietf-yang-types {
        prefix "yang";
        description 
            "External YANG module.";
    }

    import rpd-session-stats-module {
        prefix "p-rpd-session-stats";
        description 
            "File path: rpd-info/rpd-l2tp-session-info/rpd-session-stats-module.yang
            https://github.com/falcon-v-systems/rphy-yang-model/blob/master/r-phy-10/rpd-info/rpd-l2tp-session-info/rpd-session-stats-module.yang";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-RpdL2tpSessionInfo {
        tlv:id 2;
        description "TLV [100.2]: RpdInfo.RpdL2tpSessionInfo";
        leaf SessionIpAddrType {
            tlv:id 1;
            tlv:repr int32;
            type enumeration {
                enum unknown  { value  0; description ""; }
                enum ipv4     { value  1; description ""; }
                enum ipv6     { value  2; description ""; }
                enum ipv4z    { value  3; description ""; }
                enum ipv6z    { value  4; description ""; }
                enum dns      { value 16; description ""; }
            }
            description
                "TLV [100.2.1]: RpdInfo.RpdL2tpSessionInfo.SessionIpAddrType
                 non-defaults: [is_key: True]";
        }

        leaf CcapLcceIpAddress {
            tlv:id 2;
            type inet:ip-address;
            description
                "TLV [100.2.2]: RpdInfo.RpdL2tpSessionInfo.CcapLcceIpAddress
                 non-defaults: [is_key: True]";
        }

        leaf RpdLcceIpAddr {
            tlv:id 3;
            type inet:ip-address;
            description
                "TLV [100.2.3]: RpdInfo.RpdL2tpSessionInfo.RpdLcceIpAddr
                 non-defaults: [is_key: True]";
        }

        leaf Direction {
            tlv:id 4;
            tlv:repr uint8;
            type enumeration {
                enum forward  { value  0; description ""; }
                enum return   { value  1; description ""; }
            }
            description
                "TLV [100.2.4]: RpdInfo.RpdL2tpSessionInfo.Direction
                 non-defaults: [is_key: True]";
        }

        leaf L2tpSessionId {
            tlv:id 5;
            type uint32;
            description
                "TLV [100.2.5]: RpdInfo.RpdL2tpSessionInfo.L2tpSessionId
                 non-defaults: [is_key: True]";
        }

        leaf CoreId {
            tlv:id 6;
            type yang:mac-address;
            description "TLV [100.2.6]: RpdInfo.RpdL2tpSessionInfo.CoreId";
        }

        leaf ConnCtrlId {
            tlv:id 7;
            type uint32;
            description "TLV [100.2.7]: RpdInfo.RpdL2tpSessionInfo.ConnCtrlId";
        }

        leaf UdpPort {
            tlv:id 8;
            type uint16;
            description "TLV [100.2.8]: RpdInfo.RpdL2tpSessionInfo.UdpPort";
        }

        leaf Description {
            tlv:id 9;
            type string;
            description "TLV [100.2.9]: RpdInfo.RpdL2tpSessionInfo.Description";
        }

        leaf SessionType {
            tlv:id 10;
            tlv:repr uint8;
            type enumeration {
                enum psp  { value  1; description ""; }
                enum mpt  { value  2; description ""; }
            }
            description "TLV [100.2.10]: RpdInfo.RpdL2tpSessionInfo.SessionType";
        }

        leaf SessionSubType {
            tlv:id 11;
            tlv:repr uint8;
            type enumeration {
                enum mptLegacy            { value  1; description ""; }
                enum pspLegacy            { value  2; description ""; }
                enum mcm                  { value  3; description ""; }
                enum pspDepiMultichannel  { value  4; description ""; }
                enum pspUepiScQam         { value  5; description ""; }
                enum pspUepiOfdma         { value  6; description ""; }
                enum pspBwReqScQam        { value  7; description ""; }
                enum pspBwReqOfdma        { value  8; description ""; }
                enum pspProbe             { value  9; description ""; }
                enum pspRngReqScQam       { value 10; description ""; }
                enum pspRngReqOfdma       { value 11; description ""; }
                enum pspMapScQam          { value 12; description ""; }
                enum pspMapOfdma          { value 13; description ""; }
                enum pspSpecman           { value 14; description ""; }
                enum pspPnm               { value 15; description ""; }
                enum psp551Fwd            { value 16; description ""; }
                enum psp551Ret            { value 17; description ""; }
                enum psp552Fwd            { value 18; description ""; }
                enum psp552Ret            { value 19; description ""; }
                enum pspNdf               { value 20; description ""; }
                enum pspNdr               { value 21; description ""; }
            }
            description "TLV [100.2.11]: RpdInfo.RpdL2tpSessionInfo.SessionSubType";
        }

        leaf MaxPayload {
            tlv:id 12;
            type uint32;
            description "TLV [100.2.12]: RpdInfo.RpdL2tpSessionInfo.MaxPayload";
        }

        leaf PathPayload {
            tlv:id 13;
            type uint32;
            description "TLV [100.2.13]: RpdInfo.RpdL2tpSessionInfo.PathPayload";
        }

        leaf RpdIfMtu {
            tlv:id 14;
            type uint32;
            description "TLV [100.2.14]: RpdInfo.RpdL2tpSessionInfo.RpdIfMtu";
        }

        leaf CoreIfMtu {
            tlv:id 15;
            type uint32;
            description "TLV [100.2.15]: RpdInfo.RpdL2tpSessionInfo.CoreIfMtu";
        }

        leaf ErrorCode {
            tlv:id 16;
            tlv:repr uint8;
            type enumeration {
                enum none                             { value  1; description ""; }
                enum invalidMACInterfaceValue         { value  2; description ""; }
                enum invalidInterfaceValue            { value  3; description ""; }
                enum noResourcesForInterfaceIndex     { value  4; description ""; }
                enum l2tpv3Error                      { value  5; description ""; }
                enum ifAdminStatusSetToDown           { value  6; description ""; }
            }
            description "TLV [100.2.16]: RpdInfo.RpdL2tpSessionInfo.ErrorCode";
        }

        leaf CreationTime {
            tlv:id 17;
            type uint32;
            description "TLV [100.2.17]: RpdInfo.RpdL2tpSessionInfo.CreationTime";
        }

        leaf OperStatus {
            tlv:id 18;
            type uint8;
            description "TLV [100.2.18]: RpdInfo.RpdL2tpSessionInfo.OperStatus";
        }

        leaf LocalStatus {
            tlv:id 19;
            tlv:repr uint8;
            type enumeration {
                enum other                { value  0; description ""; }
                enum pwNotForwarding      { value  1; description ""; }
                enum servicePwRxFault     { value  2; description ""; }
                enum servicePwTxFault     { value  3; description ""; }
                enum psnPwRxFault         { value  4; description ""; }
                enum psnPwTxFault         { value  5; description ""; }
            }
            description "TLV [100.2.19]: RpdInfo.RpdL2tpSessionInfo.LocalStatus";
        }

        leaf LastChange {
            tlv:id 20;
            type uint32;
            description "TLV [100.2.20]: RpdInfo.RpdL2tpSessionInfo.LastChange";
        }

        container RpdSessionStats {
            tlv:id 21;
            description "TLV [100.2.21]: RpdInfo.RpdL2tpSessionInfo.RpdSessionStats";
            uses "p-rpd-session-stats:g-RpdSessionStats";
        }

    }  // g-RpdL2tpSessionInfo grouping

}
