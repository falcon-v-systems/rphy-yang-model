module rpd-session-stats-module {
    yang-version 1;
    /* This file is automatically generated with Falcon V System's script.
       Any change made to this file will be lost. */

    namespace "falconvsystems:r-phy-10:rpd-session-stats-module";
    prefix "p-rpd-session-stats";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-RpdSessionStats {
        tlv:id 21;
        description "TLV [100.2.21]: RpdInfo.RpdL2tpSessionInfo.RpdSessionStats";
        leaf OutOfSequencePackets {
            tlv:id 1;
            type uint32;
            description
                "TLV [100.2.21.1]: RpdInfo.RpdL2tpSessionInfo.RpdSessionStats.OutOfSequencePackets";
        }

        leaf InPackets {
            tlv:id 2;
            type uint64;
            description
                "TLV [100.2.21.2]: RpdInfo.RpdL2tpSessionInfo.RpdSessionStats.InPackets";
        }

        leaf InDiscards {
            tlv:id 3;
            type uint64;
            description
                "TLV [100.2.21.3]: RpdInfo.RpdL2tpSessionInfo.RpdSessionStats.InDiscards";
        }

        leaf OutPackets {
            tlv:id 4;
            type uint64;
            description
                "TLV [100.2.21.4]: RpdInfo.RpdL2tpSessionInfo.RpdSessionStats.OutPackets";
        }

        leaf OutErrors {
            tlv:id 5;
            type uint64;
            description
                "TLV [100.2.21.5]: RpdInfo.RpdL2tpSessionInfo.RpdSessionStats.OutErrors";
        }

        leaf CounterDiscontinuityTime {
            tlv:id 6;
            type binary;
            description
                "TLV [100.2.21.6]: RpdInfo.RpdL2tpSessionInfo.RpdSessionStats.CounterDiscontinuityTime";
        }

    }  // g-RpdSessionStats grouping

}
