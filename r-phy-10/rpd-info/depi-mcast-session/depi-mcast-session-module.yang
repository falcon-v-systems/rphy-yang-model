module depi-mcast-session-module {
    yang-version 1;
    /* This file is automatically generated with Falcon V System's script.
       Any change made to this file will be lost. */

    namespace "falconvsystems:r-phy-10:depi-mcast-session-module";
    prefix "p-depi-mcast-session";

    // --- imports ---------------------------------------

    import ietf-inet-types {
        prefix "inet";
        description 
            "External YANG module.";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-DepiMcastSession {
        tlv:id 5;
        description "TLV [100.5]: RpdInfo.DepiMcastSession";
        leaf IpAddrType {
            tlv:id 1;
            tlv:repr int32;
            type enumeration {
                enum unknown  { value  0; description ""; }
                enum ipv4     { value  1; description ""; }
                enum ipv6     { value  2; description ""; }
                enum ipv4z    { value  3; description ""; }
                enum ipv6z    { value  4; description ""; }
                enum dns      { value 16; description ""; }
            }
            description
                "TLV [100.5.1]: RpdInfo.DepiMcastSession.IpAddrType
                 non-defaults: [is_key: True]";
        }

        leaf GroupIpAddr {
            tlv:id 2;
            type inet:ip-address;
            description
                "TLV [100.5.2]: RpdInfo.DepiMcastSession.GroupIpAddr
                 non-defaults: [is_key: True]";
        }

        leaf SrcIpAddr {
            tlv:id 3;
            type inet:ip-address;
            description
                "TLV [100.5.3]: RpdInfo.DepiMcastSession.SrcIpAddr
                 non-defaults: [is_key: True]";
        }

        leaf RpdLcceIpAddr {
            tlv:id 4;
            type inet:ip-address;
            description "TLV [100.5.4]: RpdInfo.DepiMcastSession.RpdLcceIpAddr";
        }

        leaf CcapLcceIpAddr {
            tlv:id 5;
            type inet:ip-address;
            description "TLV [100.5.5]: RpdInfo.DepiMcastSession.CcapLcceIpAddr";
        }

        leaf L2tpSessionId {
            tlv:id 6;
            type uint32;
            description
                "TLV [100.5.6]: RpdInfo.DepiMcastSession.L2tpSessionId
                 non-defaults: [is_key: True]";
        }

        leaf JoinTime {
            tlv:id 7;
            type binary;
            description "TLV [100.5.7]: RpdInfo.DepiMcastSession.JoinTime";
        }

    }  // g-DepiMcastSession grouping

}
