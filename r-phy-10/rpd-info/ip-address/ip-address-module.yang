module ip-address-module {
    yang-version 1;
    /* This file is automatically generated with Falcon V System's script.
       Any change made to this file will be lost. */

    namespace "falconvsystems:r-phy-10:ip-address-module";
    prefix "p-ip-address";

    // --- imports ---------------------------------------

    import ietf-inet-types {
        prefix "inet";
        description 
            "External YANG module.";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-IpAddress {
        tlv:id 15;
        description "TLV [100.15]: RpdInfo.IpAddress";
        leaf AddrType {
            tlv:id 1;
            tlv:repr int32;
            type enumeration {
                enum unknown  { value  0; description ""; }
                enum ipv4     { value  1; description ""; }
                enum ipv6     { value  2; description ""; }
                enum ipv4z    { value  3; description ""; }
                enum ipv6z    { value  4; description ""; }
                enum dns      { value 16; description ""; }
            }
            description
                "TLV [100.15.1]: RpdInfo.IpAddress.AddrType
                 non-defaults: [is_key: True]";
        }

        leaf IpAddress {
            tlv:id 2;
            type inet:ip-address;
            description
                "TLV [100.15.2]: RpdInfo.IpAddress.IpAddress
                 non-defaults: [is_key: True]";
        }

        leaf EnetPortIndex {
            tlv:id 3;
            type uint8;
            description "TLV [100.15.3]: RpdInfo.IpAddress.EnetPortIndex";
        }

        leaf Type {
            tlv:id 4;
            tlv:repr uint8;
            type enumeration {
                enum unicast      { value  1; description ""; }
                enum anycast      { value  2; description ""; }
                enum broadcast    { value  3; description ""; }
            }
            description "TLV [100.15.4]: RpdInfo.IpAddress.Type";
        }

        leaf PrefixLen {
            tlv:id 5;
            type uint16;
            description "TLV [100.15.5]: RpdInfo.IpAddress.PrefixLen";
        }

        leaf Origin {
            tlv:id 6;
            tlv:repr uint8;
            type enumeration {
                enum other        { value  1; description ""; }
                enum manual       { value  2; description ""; }
                enum wellKnown    { value  3; description ""; }
                enum dhcp         { value  4; description ""; }
                enum routerAdv    { value  5; description ""; }
            }
            description "TLV [100.15.6]: RpdInfo.IpAddress.Origin";
        }

        leaf Status {
            tlv:id 7;
            tlv:repr uint8;
            type enumeration {
                enum preferred        { value  1; description ""; }
                enum deprecated       { value  2; description ""; }
                enum invalid          { value  3; description ""; }
                enum inaccessible     { value  4; description ""; }
                enum unknown          { value  5; description ""; }
                enum tentative        { value  6; description ""; }
                enum duplicate        { value  7; description ""; }
                enum optimistic       { value  8; description ""; }
            }
            description "TLV [100.15.7]: RpdInfo.IpAddress.Status";
        }

        leaf Created {
            tlv:id 8;
            type uint32;
            description "TLV [100.15.8]: RpdInfo.IpAddress.Created";
        }

        leaf LastChanged {
            tlv:id 9;
            type uint32;
            description "TLV [100.15.9]: RpdInfo.IpAddress.LastChanged";
        }

    }  // g-IpAddress grouping

}
