module ip-if-stats-module {
    yang-version 1;
    /* This file is automatically generated with Falcon V System's script.
       Any change made to this file will be lost. */

    namespace "falconvsystems:r-phy-10:ip-if-stats-module";
    prefix "p-ip-if-stats";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-IpIfStats {
        tlv:id 14;
        description "TLV [100.14]: RpdInfo.IpIfStats";
        leaf IpVersion {
            tlv:id 1;
            type uint8;
            description
                "TLV [100.14.1]: RpdInfo.IpIfStats.IpVersion
                 non-defaults: [is_key: True]";
        }

        leaf EnetPortIndex {
            tlv:id 2;
            type uint8;
            description
                "TLV [100.14.2]: RpdInfo.IpIfStats.EnetPortIndex
                 non-defaults: [is_key: True]";
        }

        leaf InReceives {
            tlv:id 3;
            type uint64;
            description "TLV [100.14.3]: RpdInfo.IpIfStats.InReceives";
        }

        leaf InOctets {
            tlv:id 4;
            type uint64;
            description "TLV [100.14.4]: RpdInfo.IpIfStats.InOctets";
        }

        leaf InHdrErrors {
            tlv:id 5;
            type uint64;
            description "TLV [100.14.5]: RpdInfo.IpIfStats.InHdrErrors";
        }

        leaf InNoRoutes {
            tlv:id 6;
            type uint64;
            description "TLV [100.14.6]: RpdInfo.IpIfStats.InNoRoutes";
        }

        leaf InAddrErrors {
            tlv:id 7;
            type uint64;
            description "TLV [100.14.7]: RpdInfo.IpIfStats.InAddrErrors";
        }

        leaf InUnknownProtos {
            tlv:id 8;
            type uint64;
            description "TLV [100.14.8]: RpdInfo.IpIfStats.InUnknownProtos";
        }

        leaf InTruncatedPkts {
            tlv:id 9;
            type uint64;
            description "TLV [100.14.9]: RpdInfo.IpIfStats.InTruncatedPkts";
        }

        leaf InDiscards {
            tlv:id 14;
            type uint64;
            description "TLV [100.14.14]: RpdInfo.IpIfStats.InDiscards";
        }

        leaf InDelivers {
            tlv:id 15;
            type uint64;
            description "TLV [100.14.15]: RpdInfo.IpIfStats.InDelivers";
        }

        leaf OutRequests {
            tlv:id 16;
            type uint64;
            description "TLV [100.14.16]: RpdInfo.IpIfStats.OutRequests";
        }

        leaf OutDiscards {
            tlv:id 18;
            type uint64;
            description "TLV [100.14.18]: RpdInfo.IpIfStats.OutDiscards";
        }

        leaf OutTransmits {
            tlv:id 23;
            type uint64;
            description "TLV [100.14.23]: RpdInfo.IpIfStats.OutTransmits";
        }

        leaf OutOctets {
            tlv:id 24;
            type uint64;
            description "TLV [100.14.24]: RpdInfo.IpIfStats.OutOctets";
        }

        leaf InMcastPkts {
            tlv:id 25;
            type uint64;
            description "TLV [100.14.25]: RpdInfo.IpIfStats.InMcastPkts";
        }

        leaf InMcastOctets {
            tlv:id 26;
            type uint64;
            description "TLV [100.14.26]: RpdInfo.IpIfStats.InMcastOctets";
        }

        leaf OutMcastPkts {
            tlv:id 27;
            type uint64;
            description "TLV [100.14.27]: RpdInfo.IpIfStats.OutMcastPkts";
        }

        leaf OutMcastOctets {
            tlv:id 28;
            type uint64;
            description "TLV [100.14.28]: RpdInfo.IpIfStats.OutMcastOctets";
        }

        leaf DiscontinuityTime {
            tlv:id 31;
            type binary;
            description "TLV [100.14.31]: RpdInfo.IpIfStats.DiscontinuityTime";
        }

        leaf RefreshRate {
            tlv:id 32;
            type uint32;
            description "TLV [100.14.32]: RpdInfo.IpIfStats.RefreshRate";
        }

    }  // g-IpIfStats grouping

}
