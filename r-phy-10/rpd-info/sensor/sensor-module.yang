module sensor-module {
    yang-version 1;
    /* This file is automatically generated with Falcon V System's script.
       Any change made to this file will be lost. */

    namespace "falconvsystems:r-phy-10:sensor-module";
    prefix "p-sensor";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-Sensor {
        tlv:id 7;
        description "TLV [100.7]: RpdInfo.Sensor";
        leaf EntityIndex {
            tlv:id 1;
            type uint32;
            description
                "TLV [100.7.1]: RpdInfo.Sensor.EntityIndex
                 non-defaults: [is_key: True]";
        }

        leaf SensorType {
            tlv:id 2;
            tlv:repr uint8;
            type enumeration {
                enum other        { value  1; description ""; }
                enum unknown      { value  2; description ""; }
                enum voltsAC      { value  3; description ""; }
                enum voltsDC      { value  4; description ""; }
                enum amperes      { value  5; description ""; }
                enum watts        { value  6; description ""; }
                enum hertz        { value  7; description ""; }
                enum celsius      { value  8; description ""; }
                enum percentRH    { value  9; description ""; }
                enum rpm          { value 10; description ""; }
                enum cmm          { value 11; description ""; }
                enum truthvalue   { value 12; description ""; }
            }
            description "TLV [100.7.2]: RpdInfo.Sensor.SensorType";
        }

        leaf Scale {
            tlv:id 3;
            tlv:repr uint8;
            type enumeration {
                enum yocto    { value  1; description ""; }
                enum zepto    { value  2; description ""; }
                enum atto     { value  3; description ""; }
                enum femto    { value  4; description ""; }
                enum pico     { value  5; description ""; }
                enum nano     { value  6; description ""; }
                enum micro    { value  7; description ""; }
                enum milli    { value  8; description ""; }
                enum units    { value  9; description ""; }
                enum kilo     { value 10; description ""; }
                enum mega     { value 11; description ""; }
                enum giga     { value 12; description ""; }
                enum tera     { value 13; description ""; }
                enum exa      { value 14; description ""; }
                enum peta     { value 15; description ""; }
                enum zetta    { value 16; description ""; }
                enum yotta    { value 17; description ""; }
            }
            description "TLV [100.7.3]: RpdInfo.Sensor.Scale";
        }

        leaf Precision {
            tlv:id 4;
            type int8;
            description "TLV [100.7.4]: RpdInfo.Sensor.Precision";
        }

        leaf Value {
            tlv:id 5;
            type int32;
            description "TLV [100.7.5]: RpdInfo.Sensor.Value";
        }

        leaf OperStatus {
            tlv:id 6;
            tlv:repr uint8;
            type enumeration {
                enum ok               { value  1; description ""; }
                enum unavailable      { value  2; description ""; }
                enum nonoperational   { value  3; description ""; }
            }
            description "TLV [100.7.6]: RpdInfo.Sensor.OperStatus";
        }

        leaf UnitsDisplay {
            tlv:id 7;
            type string;
            description "TLV [100.7.7]: RpdInfo.Sensor.UnitsDisplay";
        }

        leaf ValueTimeStamp {
            tlv:id 8;
            type uint32;
            description "TLV [100.7.8]: RpdInfo.Sensor.ValueTimeStamp";
        }

        leaf ValueUpdateRate {
            tlv:id 9;
            type uint32;
            description "TLV [100.7.9]: RpdInfo.Sensor.ValueUpdateRate";
        }

    }  // g-Sensor grouping

}
