module host-resources-storage-module {
    yang-version 1;
    /* This file is automatically generated with Falcon V System's script.
       Any change made to this file will be lost. */

    namespace "falconvsystems:r-phy-10:host-resources-storage-module";
    prefix "p-host-resources-storage";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-HostResourcesStorage {
        tlv:id 22;
        description "TLV [100.22]: RpdInfo.HostResourcesStorage";
        leaf Index {
            tlv:id 1;
            type uint32;
            description
                "TLV [100.22.1]: RpdInfo.HostResourcesStorage.Index
                 non-defaults: [is_key: True]";
        }

        leaf Type {
            tlv:id 2;
            tlv:repr uint8;
            type enumeration {
                enum other            { value  1; description ""; }
                enum ram              { value  2; description ""; }
                enum virtualMemory    { value  3; description ""; }
                enum fixedDisk        { value  4; description ""; }
                enum removableDisk    { value  5; description ""; }
                enum floppyDisk       { value  6; description ""; }
                enum compactDisc      { value  7; description ""; }
                enum ramDisk          { value  8; description ""; }
                enum flashMemory      { value  9; description ""; }
                enum networkDisk      { value 10; description ""; }
            }
            description "TLV [100.22.2]: RpdInfo.HostResourcesStorage.Type";
        }

        leaf AllocationUnits {
            tlv:id 3;
            type uint32;
            description "TLV [100.22.3]: RpdInfo.HostResourcesStorage.AllocationUnits";
        }

        leaf AllocationFailures {
            tlv:id 4;
            type uint64;
            description
                "TLV [100.22.4]: RpdInfo.HostResourcesStorage.AllocationFailures";
        }

        leaf Size {
            tlv:id 5;
            type uint32;
            description "TLV [100.22.5]: RpdInfo.HostResourcesStorage.Size";
        }

        leaf Used {
            tlv:id 6;
            type uint32;
            description "TLV [100.22.6]: RpdInfo.HostResourcesStorage.Used";
        }

        leaf Descr {
            tlv:id 7;
            type string;
            description "TLV [100.22.7]: RpdInfo.HostResourcesStorage.Descr";
        }

    }  // g-HostResourcesStorage grouping

}
