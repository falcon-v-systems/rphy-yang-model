module host-resources-system-module {
    yang-version 1;
    /* This file is automatically generated with Falcon V System's script.
       Any change made to this file will be lost. */

    namespace "falconvsystems:r-phy-10:host-resources-system-module";
    prefix "p-host-resources-system";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-HostResourcesSystem {
        tlv:id 21;
        description "TLV [100.21]: RpdInfo.HostResourcesSystem";
        leaf Date {
            tlv:id 1;
            type binary;
            description "TLV [100.21.1]: RpdInfo.HostResourcesSystem.Date";
        }

    }  // g-HostResourcesSystem grouping

}
