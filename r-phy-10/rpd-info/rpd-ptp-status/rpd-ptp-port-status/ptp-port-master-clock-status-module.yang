module ptp-port-master-clock-status-module {
    yang-version 1;
    /* This file is automatically generated with Falcon V System's script.
       Any change made to this file will be lost. */

    namespace "falconvsystems:r-phy-10:ptp-port-master-clock-status-module";
    prefix "p-ptp-port-master-clock-status";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-PtpPortMasterClockStatus {
        tlv:id 6;
        description
            "TLV [100.24.4.6]: RpdInfo.RpdPtpStatus.RpdPtpPortStatus.PtpPortMasterClockStatus";
        leaf MasterPriority {
            tlv:id 1;
            type uint8;
            description
                "TLV [100.24.4.6.1]: RpdInfo.RpdPtpStatus.RpdPtpPortStatus.PtpPortMasterClockStatus.MasterPriority
                 non-defaults: [is_key: True]";
        }

        leaf PacketsSent {
            tlv:id 2;
            type uint64;
            description
                "TLV [100.24.4.6.2]: RpdInfo.RpdPtpStatus.RpdPtpPortStatus.PtpPortMasterClockStatus.PacketsSent";
        }

        leaf PacketsReceived {
            tlv:id 3;
            type uint64;
            description
                "TLV [100.24.4.6.3]: RpdInfo.RpdPtpStatus.RpdPtpPortStatus.PtpPortMasterClockStatus.PacketsReceived";
        }

        leaf MasterClockId {
            tlv:id 4;
            type binary;
            description
                "TLV [100.24.4.6.4]: RpdInfo.RpdPtpStatus.RpdPtpPortStatus.PtpPortMasterClockStatus.MasterClockId";
        }

        leaf MasterClockPortNumber {
            tlv:id 5;
            type uint16;
            description
                "TLV [100.24.4.6.5]: RpdInfo.RpdPtpStatus.RpdPtpPortStatus.PtpPortMasterClockStatus.MasterClockPortNumber";
        }

        leaf TwoStepFlag {
            tlv:id 6;
            type boolean;
            description
                "TLV [100.24.4.6.6]: RpdInfo.RpdPtpStatus.RpdPtpPortStatus.PtpPortMasterClockStatus.TwoStepFlag";
        }

        leaf IsBmc {
            tlv:id 7;
            type boolean;
            description
                "TLV [100.24.4.6.7]: RpdInfo.RpdPtpStatus.RpdPtpPortStatus.PtpPortMasterClockStatus.IsBmc";
        }

        leaf IsMasterConnected {
            tlv:id 8;
            type boolean;
            description
                "TLV [100.24.4.6.8]: RpdInfo.RpdPtpStatus.RpdPtpPortStatus.PtpPortMasterClockStatus.IsMasterConnected";
        }

        leaf StatusDomain {
            tlv:id 9;
            type uint32;
            description
                "TLV [100.24.4.6.9]: RpdInfo.RpdPtpStatus.RpdPtpPortStatus.PtpPortMasterClockStatus.StatusDomain";
        }

        leaf FreqOffset {
            tlv:id 10;
            type uint32;
            description
                "TLV [100.24.4.6.10]: RpdInfo.RpdPtpStatus.RpdPtpPortStatus.PtpPortMasterClockStatus.FreqOffset";
        }

        leaf CounterDiscontinuityTime {
            tlv:id 11;
            type binary;
            description
                "TLV [100.24.4.6.11]: RpdInfo.RpdPtpStatus.RpdPtpPortStatus.PtpPortMasterClockStatus.CounterDiscontinuityTime";
        }

        leaf GmClockIdentity {
            tlv:id 12;
            type binary;
            description
                "TLV [100.24.4.6.12]: RpdInfo.RpdPtpStatus.RpdPtpPortStatus.PtpPortMasterClockStatus.GmClockIdentity";
        }

        leaf GmPriority1 {
            tlv:id 13;
            type uint8;
            description
                "TLV [100.24.4.6.13]: RpdInfo.RpdPtpStatus.RpdPtpPortStatus.PtpPortMasterClockStatus.GmPriority1";
        }

        leaf GmPriority2 {
            tlv:id 14;
            type uint8;
            description
                "TLV [100.24.4.6.14]: RpdInfo.RpdPtpStatus.RpdPtpPortStatus.PtpPortMasterClockStatus.GmPriority2";
        }

        leaf GmQualityClass {
            tlv:id 15;
            type uint8;
            description
                "TLV [100.24.4.6.15]: RpdInfo.RpdPtpStatus.RpdPtpPortStatus.PtpPortMasterClockStatus.GmQualityClass";
        }

        leaf GmQualityAccuracy {
            tlv:id 16;
            type uint8;
            description
                "TLV [100.24.4.6.16]: RpdInfo.RpdPtpStatus.RpdPtpPortStatus.PtpPortMasterClockStatus.GmQualityAccuracy";
        }

        leaf GmQualityOffset {
            tlv:id 17;
            type uint16;
            description
                "TLV [100.24.4.6.17]: RpdInfo.RpdPtpStatus.RpdPtpPortStatus.PtpPortMasterClockStatus.GmQualityOffset";
        }

        leaf GmStepsRemoved {
            tlv:id 18;
            type uint32;
            description
                "TLV [100.24.4.6.18]: RpdInfo.RpdPtpStatus.RpdPtpPortStatus.PtpPortMasterClockStatus.GmStepsRemoved";
        }

    }  // g-PtpPortMasterClockStatus grouping

}
