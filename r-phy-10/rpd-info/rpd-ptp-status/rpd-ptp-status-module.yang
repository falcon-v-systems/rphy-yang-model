module rpd-ptp-status-module {
    yang-version 1;
    /* This file is automatically generated with Falcon V System's script.
       Any change made to this file will be lost. */

    namespace "falconvsystems:r-phy-10:rpd-ptp-status-module";
    prefix "p-rpd-ptp-status";

    // --- imports ---------------------------------------

    import ptp-clock-status-module {
        prefix "p-ptp-clock-status";
        description 
            "File path: rpd-info/rpd-ptp-status/ptp-clock-status-module.yang
            https://github.com/falcon-v-systems/rphy-yang-model/blob/master/r-phy-10/rpd-info/rpd-ptp-status/ptp-clock-status-module.yang";
    }

    import ptp-current-dataset-module {
        prefix "p-ptp-current-dataset";
        description 
            "File path: rpd-info/rpd-ptp-status/ptp-current-dataset-module.yang
            https://github.com/falcon-v-systems/rphy-yang-model/blob/master/r-phy-10/rpd-info/rpd-ptp-status/ptp-current-dataset-module.yang";
    }

    import ptp-port-dataset-module {
        prefix "p-ptp-port-dataset";
        description 
            "File path: rpd-info/rpd-ptp-status/ptp-port-dataset-module.yang
            https://github.com/falcon-v-systems/rphy-yang-model/blob/master/r-phy-10/rpd-info/rpd-ptp-status/ptp-port-dataset-module.yang";
    }

    import rpd-ptp-port-status-module {
        prefix "p-rpd-ptp-port-status";
        description 
            "File path: rpd-info/rpd-ptp-status/rpd-ptp-port-status/rpd-ptp-port-status-module.yang
            https://github.com/falcon-v-systems/rphy-yang-model/blob/master/r-phy-10/rpd-info/rpd-ptp-status/rpd-ptp-port-status/rpd-ptp-port-status-module.yang";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-RpdPtpStatus {
        tlv:id 24;
        description "TLV [100.24]: RpdInfo.RpdPtpStatus";
        container PtpCurrentDataset {
            tlv:id 1;
            description "TLV [100.24.1]: RpdInfo.RpdPtpStatus.PtpCurrentDataset";
            uses "p-ptp-current-dataset:g-PtpCurrentDataset";
        }

        container PtpClockStatus {
            tlv:id 2;
            description "TLV [100.24.2]: RpdInfo.RpdPtpStatus.PtpClockStatus";
            uses "p-ptp-clock-status:g-PtpClockStatus";
        }

        list PtpPortDataset {
            tlv:id 3;
            key PortNumber;
            description "TLV [100.24.3]: RpdInfo.RpdPtpStatus.PtpPortDataset";
            uses "p-ptp-port-dataset:g-PtpPortDataset";
        }

        list RpdPtpPortStatus {
            tlv:id 4;
            key RpdEnetPortIndex RpdPtpPortIndex;
            description "TLV [100.24.4]: RpdInfo.RpdPtpStatus.RpdPtpPortStatus";
            uses "p-rpd-ptp-port-status:g-RpdPtpPortStatus";
        }

    }  // g-RpdPtpStatus grouping

}
