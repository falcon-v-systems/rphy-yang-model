module rpd-cert-module {
    yang-version 1;
    /* This file is automatically generated with Falcon V System's script.
       Any change made to this file will be lost. */

    namespace "falconvsystems:r-phy-10:rpd-cert-module";
    prefix "p-rpd-cert";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-RpdCert {
        tlv:id 26;
        description "TLV [100.26]: RpdInfo.RpdCert";
        leaf DeviceCert {
            tlv:id 1;
            type binary;
            description "TLV [100.26.1]: RpdInfo.RpdCert.DeviceCert";
        }

        leaf SigningCaCert {
            tlv:id 2;
            type binary;
            description "TLV [100.26.2]: RpdInfo.RpdCert.SigningCaCert";
        }

    }  // g-RpdCert grouping

}
