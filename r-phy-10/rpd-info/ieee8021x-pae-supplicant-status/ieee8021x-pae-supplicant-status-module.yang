module ieee8021x-pae-supplicant-status-module {
    yang-version 1;
    /* This file is automatically generated with Falcon V System's script.
       Any change made to this file will be lost. */

    namespace "falconvsystems:r-phy-10:ieee8021x-pae-supplicant-status-module";
    prefix "p-ieee8021x-pae-supplicant-status";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-Ieee8021xPaeSupplicantStatus {
        tlv:id 30;
        description "TLV [100.30]: RpdInfo.Ieee8021xPaeSupplicantStatus";
        leaf PortNumber {
            tlv:id 1;
            type uint32;
            description
                "TLV [100.30.1]: RpdInfo.Ieee8021xPaeSupplicantStatus.PortNumber
                 non-defaults: [is_key: True]";
        }

        leaf Authenticated {
            tlv:id 2;
            type boolean;
            description
                "TLV [100.30.2]: RpdInfo.Ieee8021xPaeSupplicantStatus.Authenticated";
        }

        leaf Failed {
            tlv:id 3;
            type boolean;
            description "TLV [100.30.3]: RpdInfo.Ieee8021xPaeSupplicantStatus.Failed";
        }

        leaf RetryCount {
            tlv:id 4;
            type uint32;
            description
                "TLV [100.30.4]: RpdInfo.Ieee8021xPaeSupplicantStatus.RetryCount";
        }

    }  // g-Ieee8021xPaeSupplicantStatus grouping

}
