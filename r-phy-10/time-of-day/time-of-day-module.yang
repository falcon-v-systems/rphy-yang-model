module time-of-day-module {
    yang-version 1;
    /* This file is automatically generated with Falcon V System's script.
       Any change made to this file will be lost. */

    namespace "falconvsystems:r-phy-10:time-of-day-module";
    prefix "p-time-of-day";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-TimeOfDay {
        tlv:id 104;
        description "TLV [104]: TimeOfDay";
        leaf TimeOfDayUpdate {
            tlv:id 1;
            tlv:repr uint8;
            type enumeration {
                enum Disabled                 { value  0; description ""; }
                enum PTP                      { value  1; description ""; }
                enum RepeatedTimeProtocol     { value  2; description ""; }
            }
            description "TLV [104.1]: TimeOfDay.TimeOfDayUpdate";
        }

    }  // g-TimeOfDay grouping

}
