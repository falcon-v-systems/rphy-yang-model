module rpd-identification-module {
    yang-version 1;
    /* This file is automatically generated with Falcon V System's script.
       Any change made to this file will be lost. */

    namespace "falconvsystems:r-phy-10:rpd-identification-module";
    prefix "p-rpd-identification";

    // --- imports ---------------------------------------

    import ietf-inet-types {
        prefix "inet";
        description 
            "External YANG module.";
    }

    import ietf-yang-types {
        prefix "yang";
        description 
            "External YANG module.";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-RpdIdentification {
        tlv:id 19;
        description
            "TLV [50.19]: RpdCapabilities.RpdIdentification
             non-defaults: [is_rcp_readonly: True, is_readonly: True]";
        leaf VendorName {
            tlv:id 1;
            type string;
            description
                "TLV [50.19.1]: RpdCapabilities.RpdIdentification.VendorName
                 non-defaults: [is_rcp_readonly: True, is_readonly: True]";
        }

        leaf VendorId {
            tlv:id 2;
            type uint16;
            description
                "TLV [50.19.2]: RpdCapabilities.RpdIdentification.VendorId
                 non-defaults: [is_rcp_readonly: True, is_readonly: True]";
        }

        leaf ModelNumber {
            tlv:id 3;
            type string;
            description
                "TLV [50.19.3]: RpdCapabilities.RpdIdentification.ModelNumber
                 non-defaults: [is_rcp_readonly: True, is_readonly: True]";
        }

        leaf DeviceMacAddress {
            tlv:id 4;
            type yang:mac-address;
            description
                "TLV [50.19.4]: RpdCapabilities.RpdIdentification.DeviceMacAddress
                 non-defaults: [is_rcp_readonly: True, is_readonly: True]";
        }

        leaf CurrentSwVersion {
            tlv:id 5;
            type string;
            description
                "TLV [50.19.5]: RpdCapabilities.RpdIdentification.CurrentSwVersion
                 non-defaults: [is_rcp_readonly: True, is_readonly: True]";
        }

        leaf BootRomVersion {
            tlv:id 6;
            type string;
            description
                "TLV [50.19.6]: RpdCapabilities.RpdIdentification.BootRomVersion
                 non-defaults: [is_rcp_readonly: True, is_readonly: True]";
        }

        leaf DeviceDescription {
            tlv:id 7;
            type string;
            description
                "TLV [50.19.7]: RpdCapabilities.RpdIdentification.DeviceDescription
                 non-defaults: [is_rcp_readonly: True, is_readonly: True]";
        }

        leaf DeviceAlias {
            tlv:id 8;
            type string;
            description "TLV [50.19.8]: RpdCapabilities.RpdIdentification.DeviceAlias";
        }

        leaf SerialNumber {
            tlv:id 9;
            type string;
            description
                "TLV [50.19.9]: RpdCapabilities.RpdIdentification.SerialNumber";
        }

        leaf UsBurstReceiverVendorId {
            tlv:id 10;
            type uint16;
            description
                "TLV [50.19.10]: RpdCapabilities.RpdIdentification.UsBurstReceiverVendorId
                 non-defaults: [is_rcp_readonly: True, is_readonly: True]";
        }

        leaf UsBurstReceiverModelNumber {
            tlv:id 11;
            type string;
            description
                "TLV [50.19.11]: RpdCapabilities.RpdIdentification.UsBurstReceiverModelNumber
                 non-defaults: [is_rcp_readonly: True, is_readonly: True]";
        }

        leaf UsBurstReceiverDriverVersion {
            tlv:id 12;
            type string;
            description
                "TLV [50.19.12]: RpdCapabilities.RpdIdentification.UsBurstReceiverDriverVersion
                 non-defaults: [is_rcp_readonly: True, is_readonly: True]";
        }

        leaf UsBurstReceiverSerialNumber {
            tlv:id 13;
            type string;
            description
                "TLV [50.19.13]: RpdCapabilities.RpdIdentification.UsBurstReceiverSerialNumber
                 non-defaults: [is_rcp_readonly: True, is_readonly: True]";
        }

        leaf RpdRcpProtocolVersion {
            tlv:id 14;
            type string;
            description
                "TLV [50.19.14]: RpdCapabilities.RpdIdentification.RpdRcpProtocolVersion
                 non-defaults: [is_rcp_readonly: True, is_readonly: True]";
        }

        leaf RpdRcpSchemaVersion {
            tlv:id 15;
            type string;
            description
                "TLV [50.19.15]: RpdCapabilities.RpdIdentification.RpdRcpSchemaVersion
                 non-defaults: [is_rcp_readonly: True, is_readonly: True]";
        }

        leaf HwRevision {
            tlv:id 16;
            type string;
            description
                "TLV [50.19.16]: RpdCapabilities.RpdIdentification.HwRevision
                 non-defaults: [is_rcp_readonly: True, is_readonly: True]";
        }

        leaf AssetId {
            tlv:id 17;
            type string;
            description "TLV [50.19.17]: RpdCapabilities.RpdIdentification.AssetId";
        }

        leaf VspSelector {
            tlv:id 18;
            type string;
            description
                "TLV [50.19.18]: RpdCapabilities.RpdIdentification.VspSelector
                 non-defaults: [is_rcp_readonly: True, is_readonly: True]";
        }

        leaf CurrentSwImageLastUpdate {
            tlv:id 19;
            type binary;
            description
                "TLV [50.19.19]: RpdCapabilities.RpdIdentification.CurrentSwImageLastUpdate
                 non-defaults: [is_rcp_readonly: True, is_readonly: True]";
        }

        leaf CurrentSwImageName {
            tlv:id 20;
            type string;
            description
                "TLV [50.19.20]: RpdCapabilities.RpdIdentification.CurrentSwImageName
                 non-defaults: [is_rcp_readonly: True, is_readonly: True]";
        }

        leaf CurrentSwImageServer {
            tlv:id 21;
            type inet:ip-address;
            description
                "TLV [50.19.21]: RpdCapabilities.RpdIdentification.CurrentSwImageServer
                 non-defaults: [is_rcp_readonly: True, is_readonly: True]";
        }

        leaf CurrentSwImageIndex {
            tlv:id 22;
            type uint8;
            description
                "TLV [50.19.22]: RpdCapabilities.RpdIdentification.CurrentSwImageIndex
                 non-defaults: [is_rcp_readonly: True, is_readonly: True]";
        }

    }  // g-RpdIdentification grouping

}
