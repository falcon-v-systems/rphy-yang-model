module spectrum-capture-capabilities-module {
    yang-version 1;
    /* This file is automatically generated with Falcon V System's script.
       Any change made to this file will be lost. */

    namespace "falconvsystems:r-phy-10:spectrum-capture-capabilities-module";
    prefix "p-spectrum-capture-capabilities";

    // --- imports ---------------------------------------

    import sac-capabilities-module {
        prefix "p-sac-capabilities";
        description 
            "File path: rpd-capabilities/spectrum-capture-capabilities/sac-capabilities-module.yang
            https://github.com/falcon-v-systems/rphy-yang-model/blob/master/r-phy-10/rpd-capabilities/spectrum-capture-capabilities/sac-capabilities-module.yang";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-SpectrumCaptureCapabilities {
        tlv:id 59;
        description
            "TLV [50.59]: RpdCapabilities.SpectrumCaptureCapabilities
             non-defaults: [is_rcp_readonly: True, is_readonly: True]";
        leaf NumSacs {
            tlv:id 1;
            type uint8;
            description
                "TLV [50.59.1]: RpdCapabilities.SpectrumCaptureCapabilities.NumSacs
                 non-defaults: [is_rcp_readonly: True, is_readonly: True]";
        }

        container SacCapabilities {
            tlv:id 2;
            description
                "TLV [50.59.2]: RpdCapabilities.SpectrumCaptureCapabilities.SacCapabilities
                 non-defaults: [is_rcp_readonly: True, is_readonly: True]";
            uses "p-sac-capabilities:g-SacCapabilities";
        }

    }  // g-SpectrumCaptureCapabilities grouping

}
