module rpd-capabilities-module {
    yang-version 1;
    /* This file is automatically generated with Falcon V System's script.
       Any change made to this file will be lost. */

    namespace "falconvsystems:r-phy-10:rpd-capabilities-module";
    prefix "p-rpd-capabilities";

    // --- imports ---------------------------------------

    import alloc-ds-chan-resources-module {
        prefix "p-alloc-ds-chan-resources";
        description 
            "File path: rpd-capabilities/alloc-ds-chan-resources/alloc-ds-chan-resources-module.yang
            https://github.com/falcon-v-systems/rphy-yang-model/blob/master/r-phy-10/rpd-capabilities/alloc-ds-chan-resources/alloc-ds-chan-resources-module.yang";
    }

    import alloc-us-chan-resources-module {
        prefix "p-alloc-us-chan-resources";
        description 
            "File path: rpd-capabilities/alloc-us-chan-resources/alloc-us-chan-resources-module.yang
            https://github.com/falcon-v-systems/rphy-yang-model/blob/master/r-phy-10/rpd-capabilities/alloc-us-chan-resources/alloc-us-chan-resources-module.yang";
    }

    import device-location-module {
        prefix "p-device-location";
        description 
            "File path: rpd-capabilities/device-location/device-location-module.yang
            https://github.com/falcon-v-systems/rphy-yang-model/blob/master/r-phy-10/rpd-capabilities/device-location/device-location-module.yang";
    }

    import ds-capabilities-module {
        prefix "p-ds-capabilities";
        description 
            "File path: rpd-capabilities/ds-capabilities/ds-capabilities-module.yang
            https://github.com/falcon-v-systems/rphy-yang-model/blob/master/r-phy-10/rpd-capabilities/ds-capabilities/ds-capabilities-module.yang";
    }

    import fdx-capabilities-module {
        prefix "p-fdx-capabilities";
        description 
            "File path: rpd-capabilities/fdx-capabilities/fdx-capabilities-module.yang
            https://github.com/falcon-v-systems/rphy-yang-model/blob/master/r-phy-10/rpd-capabilities/fdx-capabilities/fdx-capabilities-module.yang";
    }

    import gcp-capabilities-module {
        prefix "p-gcp-capabilities";
        description 
            "File path: rpd-capabilities/gcp-capabilities/gcp-capabilities-module.yang
            https://github.com/falcon-v-systems/rphy-yang-model/blob/master/r-phy-10/rpd-capabilities/gcp-capabilities/gcp-capabilities-module.yang";
    }

    import lcce-channel-reachability-module {
        prefix "p-lcce-channel-reachability";
        description 
            "File path: rpd-capabilities/lcce-channel-reachability/lcce-channel-reachability-module.yang
            https://github.com/falcon-v-systems/rphy-yang-model/blob/master/r-phy-10/rpd-capabilities/lcce-channel-reachability/lcce-channel-reachability-module.yang";
    }

    import ofdm-configuration-capabilities-module {
        prefix "p-ofdm-configuration-capabilities";
        description 
            "File path: rpd-capabilities/ofdm-configuration-capabilities/ofdm-configuration-capabilities-module.yang
            https://github.com/falcon-v-systems/rphy-yang-model/blob/master/r-phy-10/rpd-capabilities/ofdm-configuration-capabilities/ofdm-configuration-capabilities-module.yang";
    }

    import pilot-tone-capabilities-module {
        prefix "p-pilot-tone-capabilities";
        description 
            "File path: rpd-capabilities/pilot-tone-capabilities/pilot-tone-capabilities-module.yang
            https://github.com/falcon-v-systems/rphy-yang-model/blob/master/r-phy-10/rpd-capabilities/pilot-tone-capabilities/pilot-tone-capabilities-module.yang";
    }

    import rdti-capabilities-module {
        prefix "p-rdti-capabilities";
        description 
            "File path: rpd-capabilities/rdti-capabilities/rdti-capabilities-module.yang
            https://github.com/falcon-v-systems/rphy-yang-model/blob/master/r-phy-10/rpd-capabilities/rdti-capabilities/rdti-capabilities-module.yang";
    }

    import reset-capabilities-module {
        prefix "p-reset-capabilities";
        description 
            "File path: rpd-capabilities/reset-capabilities/reset-capabilities-module.yang
            https://github.com/falcon-v-systems/rphy-yang-model/blob/master/r-phy-10/rpd-capabilities/reset-capabilities/reset-capabilities-module.yang";
    }

    import rpd-core-redundancy-capabilities-module {
        prefix "p-rpd-core-redundancy-capabilities";
        description 
            "File path: rpd-capabilities/rpd-core-redundancy-capabilities/rpd-core-redundancy-capabilities-module.yang
            https://github.com/falcon-v-systems/rphy-yang-model/blob/master/r-phy-10/rpd-capabilities/rpd-core-redundancy-capabilities/rpd-core-redundancy-capabilities-module.yang";
    }

    import rpd-identification-module {
        prefix "p-rpd-identification";
        description 
            "File path: rpd-capabilities/rpd-identification/rpd-identification-module.yang
            https://github.com/falcon-v-systems/rphy-yang-model/blob/master/r-phy-10/rpd-capabilities/rpd-identification/rpd-identification-module.yang";
    }

    import spectrum-capture-capabilities-module {
        prefix "p-spectrum-capture-capabilities";
        description 
            "File path: rpd-capabilities/spectrum-capture-capabilities/spectrum-capture-capabilities-module.yang
            https://github.com/falcon-v-systems/rphy-yang-model/blob/master/r-phy-10/rpd-capabilities/spectrum-capture-capabilities/spectrum-capture-capabilities-module.yang";
    }

    import static-pw-capabilities-module {
        prefix "p-static-pw-capabilities";
        description 
            "File path: rpd-capabilities/static-pw-capabilities/static-pw-capabilities-module.yang
            https://github.com/falcon-v-systems/rphy-yang-model/blob/master/r-phy-10/rpd-capabilities/static-pw-capabilities/static-pw-capabilities-module.yang";
    }

    import sw-image-capabilities-module {
        prefix "p-sw-image-capabilities";
        description 
            "File path: rpd-capabilities/sw-image-capabilities/sw-image-capabilities-module.yang
            https://github.com/falcon-v-systems/rphy-yang-model/blob/master/r-phy-10/rpd-capabilities/sw-image-capabilities/sw-image-capabilities-module.yang";
    }

    import tlv-ext {
        prefix "tlv";
        description 
            "Falcon's Yang extension for TLV attributes.";
    }

    import us-power-capabilities-module {
        prefix "p-us-power-capabilities";
        description 
            "File path: rpd-capabilities/us-power-capabilities/us-power-capabilities-module.yang
            https://github.com/falcon-v-systems/rphy-yang-model/blob/master/r-phy-10/rpd-capabilities/us-power-capabilities/us-power-capabilities-module.yang";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-RpdCapabilities {
        tlv:id 50;
        description
            "TLV [50]: RpdCapabilities
             non-defaults: [is_rcp_readonly: True, is_readonly: True]";
        leaf NumBdirPorts {
            tlv:id 1;
            type uint16;
            description
                "TLV [50.1]: RpdCapabilities.NumBdirPorts
                 non-defaults: [is_rcp_readonly: True, is_readonly: True]";
        }

        leaf NumDsRfPorts {
            tlv:id 2;
            type uint16;
            description
                "TLV [50.2]: RpdCapabilities.NumDsRfPorts
                 non-defaults: [is_rcp_readonly: True, is_readonly: True]";
        }

        leaf NumUsRfPorts {
            tlv:id 3;
            type uint16;
            description
                "TLV [50.3]: RpdCapabilities.NumUsRfPorts
                 non-defaults: [is_rcp_readonly: True, is_readonly: True]";
        }

        leaf NumTenGeNsPorts {
            tlv:id 4;
            type uint16;
            description
                "TLV [50.4]: RpdCapabilities.NumTenGeNsPorts
                 non-defaults: [is_rcp_readonly: True, is_readonly: True]";
        }

        leaf NumOneGeNsPorts {
            tlv:id 5;
            type uint16;
            description
                "TLV [50.5]: RpdCapabilities.NumOneGeNsPorts
                 non-defaults: [is_rcp_readonly: True, is_readonly: True]";
        }

        leaf NumDsScQamChannels {
            tlv:id 6;
            type uint16;
            description
                "TLV [50.6]: RpdCapabilities.NumDsScQamChannels
                 non-defaults: [is_rcp_readonly: True, is_readonly: True]";
        }

        leaf NumDsOfdmChannels {
            tlv:id 7;
            type uint16;
            description
                "TLV [50.7]: RpdCapabilities.NumDsOfdmChannels
                 non-defaults: [is_rcp_readonly: True, is_readonly: True]";
        }

        leaf NumUsScQamChannels {
            tlv:id 8;
            type uint16;
            description
                "TLV [50.8]: RpdCapabilities.NumUsScQamChannels
                 non-defaults: [is_rcp_readonly: True, is_readonly: True]";
        }

        leaf NumUsOfdmaChannels {
            tlv:id 9;
            type uint16;
            description
                "TLV [50.9]: RpdCapabilities.NumUsOfdmaChannels
                 non-defaults: [is_rcp_readonly: True, is_readonly: True]";
        }

        leaf NumDsOob55d1Channels {
            tlv:id 10;
            tlv:repr uint16;
            type enumeration {
                enum 0    { value  0; description ""; }
                enum 1    { value  1; description ""; }
                enum 2    { value  2; description ""; }
            }
            description
                "TLV [50.10]: RpdCapabilities.NumDsOob55d1Channels
                 non-defaults: [is_rcp_readonly: True, is_readonly: True]";
        }

        leaf NumUsOob55d1Channels {
            tlv:id 11;
            type uint16;
            description
                "TLV [50.11]: RpdCapabilities.NumUsOob55d1Channels
                 non-defaults: [is_rcp_readonly: True, is_readonly: True]";
        }

        leaf NumOob55d2Modules {
            tlv:id 12;
            type uint16;
            description
                "TLV [50.12]: RpdCapabilities.NumOob55d2Modules
                 non-defaults: [is_rcp_readonly: True, is_readonly: True]";
        }

        leaf NumUsOob55d2Demodulators {
            tlv:id 13;
            type uint16;
            description
                "TLV [50.13]: RpdCapabilities.NumUsOob55d2Demodulators
                 non-defaults: [is_rcp_readonly: True, is_readonly: True]";
        }

        leaf NumNdfChannels {
            tlv:id 14;
            type uint16;
            description
                "TLV [50.14]: RpdCapabilities.NumNdfChannels
                 non-defaults: [is_rcp_readonly: True, is_readonly: True]";
        }

        leaf NumNdrChannels {
            tlv:id 15;
            type uint16;
            description
                "TLV [50.15]: RpdCapabilities.NumNdrChannels
                 non-defaults: [is_rcp_readonly: True, is_readonly: True]";
        }

        leaf SupportsUdpEncap {
            tlv:id 16;
            type boolean;
            description
                "TLV [50.16]: RpdCapabilities.SupportsUdpEncap
                 non-defaults: [is_rcp_readonly: True, is_readonly: True]";
        }

        leaf NumDsPspFlows {
            tlv:id 17;
            type uint8;
            description
                "TLV [50.17]: RpdCapabilities.NumDsPspFlows
                 non-defaults: [is_rcp_readonly: True, is_readonly: True]";
        }

        leaf NumUsPspFlows {
            tlv:id 18;
            type uint8;
            description
                "TLV [50.18]: RpdCapabilities.NumUsPspFlows
                 non-defaults: [is_rcp_readonly: True, is_readonly: True]";
        }

        container RpdIdentification {
            tlv:id 19;
            description
                "TLV [50.19]: RpdCapabilities.RpdIdentification
                 non-defaults: [is_rcp_readonly: True, is_readonly: True]";
            uses "p-rpd-identification:g-RpdIdentification";
        }

        list LcceChannelReachability {
            tlv:id 20;
            key EnetPortIndex ChannelType RfPortIndex;
            description
                "TLV [50.20]: RpdCapabilities.LcceChannelReachability
                 non-defaults: [is_rcp_readonly: True, is_readonly: True]";
            uses "p-lcce-channel-reachability:g-LcceChannelReachability";
        }

        container PilotToneCapabilities {
            tlv:id 21;
            description
                "TLV [50.21]: RpdCapabilities.PilotToneCapabilities
                 non-defaults: [is_rcp_readonly: True, is_readonly: True]";
            uses "p-pilot-tone-capabilities:g-PilotToneCapabilities";
        }

        list AllocDsChanResources {
            tlv:id 22;
            key DsPortIndex;
            description
                "TLV [50.22]: RpdCapabilities.AllocDsChanResources
                 non-defaults: [is_rcp_readonly: True, is_readonly: True]";
            uses "p-alloc-ds-chan-resources:g-AllocDsChanResources";
        }

        list AllocUsChanResources {
            tlv:id 23;
            key UsPortIndex;
            description
                "TLV [50.23]: RpdCapabilities.AllocUsChanResources
                 non-defaults: [is_rcp_readonly: True, is_readonly: True]";
            uses "p-alloc-us-chan-resources:g-AllocUsChanResources";
        }

        container DeviceLocation {
            tlv:id 24;
            description
                "TLV [50.24]: RpdCapabilities.DeviceLocation
                 non-defaults: [is_rcp_readonly: True, is_readonly: True]";
            uses "p-device-location:g-DeviceLocation";
        }

        leaf NumAsyncVideoChannels {
            tlv:id 25;
            type uint8;
            description
                "TLV [50.25]: RpdCapabilities.NumAsyncVideoChannels
                 non-defaults: [is_rcp_readonly: True, is_readonly: True]";
        }

        leaf SupportsFlowTags {
            tlv:id 26;
            type boolean;
            description
                "TLV [50.26]: RpdCapabilities.SupportsFlowTags
                 non-defaults: [is_rcp_readonly: True, is_readonly: True]";
        }

        leaf SupportsFrequencyTilt {
            tlv:id 27;
            type boolean;
            description
                "TLV [50.27]: RpdCapabilities.SupportsFrequencyTilt
                 non-defaults: [is_rcp_readonly: True, is_readonly: True]";
        }

        leaf MaxTiltValue {
            tlv:id 28;
            type uint16;
            units "TenthdB";
            description
                "TLV [50.28]: RpdCapabilities.MaxTiltValue
                 non-defaults: [is_rcp_readonly: True, is_readonly: True]";
        }

        leaf BufferDepthMonitorAlertSupport {
            tlv:id 29;
            type uint8;
            description
                "TLV [50.29]: RpdCapabilities.BufferDepthMonitorAlertSupport
                 non-defaults: [is_rcp_readonly: True, is_readonly: True]";
        }

        leaf BufferDepthConfigurationSupport {
            tlv:id 30;
            type uint8;
            description
                "TLV [50.30]: RpdCapabilities.BufferDepthConfigurationSupport
                 non-defaults: [is_rcp_readonly: True, is_readonly: True]";
        }

        leaf RpdUcdProcessingTime {
            tlv:id 31;
            type uint16;
            units "microseconds";
            description
                "TLV [50.31]: RpdCapabilities.RpdUcdProcessingTime
                 non-defaults: [is_rcp_readonly: True, is_readonly: True]";
        }

        leaf RpdUcdChangeNullGrantTime {
            tlv:id 32;
            type uint16;
            units "microseconds";
            description
                "TLV [50.32]: RpdCapabilities.RpdUcdChangeNullGrantTime
                 non-defaults: [is_rcp_readonly: True, is_readonly: True]";
        }

        leaf SupportMultiSectionTimingMerReporting {
            tlv:id 33;
            tlv:repr uint8;
            type enumeration {
                enum NoSupportMultisectionTimingAndMERReporting {
                    value  0;
                    description "";
                }
                enum SupportEquallySpacedNonOverlappingSections {
                    value  1;
                    description "";
                }
                enum SupportFullyFlexibleSectionsAndSpacingOfNonOverlappingSections {
                    value  2;
                    description "";
                }
            }
            description
                "TLV [50.33]: RpdCapabilities.SupportMultiSectionTimingMerReporting
                 non-defaults: [is_rcp_readonly: True, is_readonly: True]";
        }

        container RdtiCapabilities {
            tlv:id 34;
            description
                "TLV [50.34]: RpdCapabilities.RdtiCapabilities
                 non-defaults: [is_rcp_readonly: True, is_readonly: True]";
            uses "p-rdti-capabilities:g-RdtiCapabilities";
        }

        leaf MaxDsPspSegCount {
            tlv:id 35;
            type uint8;
            description
                "TLV [50.35]: RpdCapabilities.MaxDsPspSegCount
                 non-defaults: [is_rcp_readonly: True, is_readonly: True]";
        }

        leaf DirectDsFlowQueueMapping {
            tlv:id 36;
            type uint8;
            description
                "TLV [50.36]: RpdCapabilities.DirectDsFlowQueueMapping
                 non-defaults: [is_rcp_readonly: True, is_readonly: True]";
        }

        leaf DsSchedulerPhbIdList {
            tlv:id 37;
            type binary;
            description
                "TLV [50.37]: RpdCapabilities.DsSchedulerPhbIdList
                 non-defaults: [is_rcp_readonly: True, is_readonly: True]";
        }

        leaf RpdPendingEvRepQueueSize {
            tlv:id 38;
            type uint16;
            description
                "TLV [50.38]: RpdCapabilities.RpdPendingEvRepQueueSize
                 non-defaults: [is_rcp_readonly: True, is_readonly: True]";
        }

        leaf RpdLocalEventLogSize {
            tlv:id 39;
            type uint32;
            description
                "TLV [50.39]: RpdCapabilities.RpdLocalEventLogSize
                 non-defaults: [is_rcp_readonly: True, is_readonly: True]";
        }

        leaf SupportsOpticalNodeRf {
            tlv:id 40;
            tlv:repr boolean;
            type enumeration {
                enum NoSupportOptialNodeRfTechnology  { value  0; description ""; }
                enum SupportOpticalNodeRfTechnology   { value  1; description ""; }
            }
            description
                "TLV [50.40]: RpdCapabilities.SupportsOpticalNodeRf
                 non-defaults: [is_rcp_readonly: True, is_readonly: True]";
        }

        leaf MaxDsFrequency {
            tlv:id 41;
            type uint32;
            units "Hz";
            description
                "TLV [50.41]: RpdCapabilities.MaxDsFrequency
                 non-defaults: [is_rcp_readonly: True, is_readonly: True]";
        }

        leaf MinDsFrequency {
            tlv:id 42;
            type uint32;
            units "Hz";
            description
                "TLV [50.42]: RpdCapabilities.MinDsFrequency
                 non-defaults: [is_rcp_readonly: True, is_readonly: True]";
        }

        leaf MaxBasePower {
            tlv:id 43;
            type uint16;
            units "TenthdB";
            description
                "TLV [50.43]: RpdCapabilities.MaxBasePower
                 non-defaults: [is_rcp_readonly: True, is_readonly: True]";
        }

        leaf MinTiltValue {
            tlv:id 44;
            type int16;
            units "TenthdB";
            description
                "TLV [50.44]: RpdCapabilities.MinTiltValue
                 non-defaults: [is_rcp_readonly: True, is_readonly: True]";
        }

        leaf MinPowerAdjustScQam {
            tlv:id 45;
            type int16;
            units "TenthdB";
            description
                "TLV [50.45]: RpdCapabilities.MinPowerAdjustScQam
                 non-defaults: [is_rcp_readonly: True, is_readonly: True]";
        }

        leaf MaxPowerAdjustScQam {
            tlv:id 46;
            type uint16;
            units "TenthdB";
            description
                "TLV [50.46]: RpdCapabilities.MaxPowerAdjustScQam
                 non-defaults: [is_rcp_readonly: True, is_readonly: True]";
        }

        leaf MinPowerAdjustOfdm {
            tlv:id 47;
            type int16;
            units "TenthdB";
            description
                "TLV [50.47]: RpdCapabilities.MinPowerAdjustOfdm
                 non-defaults: [is_rcp_readonly: True, is_readonly: True]";
        }

        leaf MaxPowerAdjustOfdm {
            tlv:id 48;
            type uint16;
            units "TenthdB";
            description
                "TLV [50.48]: RpdCapabilities.MaxPowerAdjustOfdm
                 non-defaults: [is_rcp_readonly: True, is_readonly: True]";
        }

        container UsPowerCapabilities {
            tlv:id 49;
            description
                "TLV [50.49]: RpdCapabilities.UsPowerCapabilities
                 non-defaults: [is_rcp_readonly: True, is_readonly: True]";
            uses "p-us-power-capabilities:g-UsPowerCapabilities";
        }

        container StaticPwCapabilities {
            tlv:id 50;
            description
                "TLV [50.50]: RpdCapabilities.StaticPwCapabilities
                 non-defaults: [is_rcp_readonly: True, is_readonly: True]";
            uses "p-static-pw-capabilities:g-StaticPwCapabilities";
        }

        container DsCapabilities {
            tlv:id 51;
            description
                "TLV [50.51]: RpdCapabilities.DsCapabilities
                 non-defaults: [is_rcp_readonly: True, is_readonly: True]";
            uses "p-ds-capabilities:g-DsCapabilities";
        }

        container GcpCapabilities {
            tlv:id 52;
            description
                "TLV [50.52]: RpdCapabilities.GcpCapabilities
                 non-defaults: [is_rcp_readonly: True, is_readonly: True]";
            uses "p-gcp-capabilities:g-GcpCapabilities";
        }

        container SwImageCapabilities {
            tlv:id 53;
            description
                "TLV [50.53]: RpdCapabilities.SwImageCapabilities
                 non-defaults: [is_rcp_readonly: True, is_readonly: True]";
            uses "p-sw-image-capabilities:g-SwImageCapabilities";
        }

        container OfdmConfigurationCapabilities {
            tlv:id 54;
            description
                "TLV [50.54]: RpdCapabilities.OfdmConfigurationCapabilities
                 non-defaults: [is_rcp_readonly: True, is_readonly: True]";
            uses "p-ofdm-configuration-capabilities:g-OfdmConfigurationCapabilities";
        }

        container ResetCapabilities {
            tlv:id 55;
            description
                "TLV [50.55]: RpdCapabilities.ResetCapabilities
                 non-defaults: [is_rcp_readonly: True, is_readonly: True]";
            uses "p-reset-capabilities:g-ResetCapabilities";
        }

        container RpdCoreRedundancyCapabilities {
            tlv:id 56;
            description
                "TLV [50.56]: RpdCapabilities.RpdCoreRedundancyCapabilities
                 non-defaults: [is_rcp_readonly: True, is_readonly: True]";
            uses "p-rpd-core-redundancy-capabilities:g-RpdCoreRedundancyCapabilities";
        }

        container FdxCapabilities {
            tlv:id 57;
            description
                "TLV [50.57]: RpdCapabilities.FdxCapabilities
                 non-defaults: [is_rcp_readonly: True, is_readonly: True]";
            uses "p-fdx-capabilities:g-FdxCapabilities";
        }

        leaf UsProfileQuerySupported {
            tlv:id 58;
            type boolean;
            description
                "TLV [50.58]: RpdCapabilities.UsProfileQuerySupported
                 non-defaults: [is_rcp_readonly: True, is_readonly: True]";
        }

        container SpectrumCaptureCapabilities {
            tlv:id 59;
            description
                "TLV [50.59]: RpdCapabilities.SpectrumCaptureCapabilities
                 non-defaults: [is_rcp_readonly: True, is_readonly: True]";
            uses "p-spectrum-capture-capabilities:g-SpectrumCaptureCapabilities";
        }

    }  // g-RpdCapabilities grouping

}
