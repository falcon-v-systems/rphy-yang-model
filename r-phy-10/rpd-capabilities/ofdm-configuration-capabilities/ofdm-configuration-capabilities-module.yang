module ofdm-configuration-capabilities-module {
    yang-version 1;
    /* This file is automatically generated with Falcon V System's script.
       Any change made to this file will be lost. */

    namespace "falconvsystems:r-phy-10:ofdm-configuration-capabilities-module";
    prefix "p-ofdm-configuration-capabilities";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-OfdmConfigurationCapabilities {
        tlv:id 54;
        description
            "TLV [50.54]: RpdCapabilities.OfdmConfigurationCapabilities
             non-defaults: [is_rcp_readonly: True, is_readonly: True]";
        leaf RequiresOfdmaImDurationConfig {
            tlv:id 1;
            type boolean;
            description
                "TLV [50.54.1]: RpdCapabilities.OfdmConfigurationCapabilities.RequiresOfdmaImDurationConfig
                 non-defaults: [is_rcp_readonly: True, is_readonly: True]";
        }

    }  // g-OfdmConfigurationCapabilities grouping

}
