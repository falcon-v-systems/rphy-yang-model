module us-power-capabilities-module {
    yang-version 1;
    /* This file is automatically generated with Falcon V System's script.
       Any change made to this file will be lost. */

    namespace "falconvsystems:r-phy-10:us-power-capabilities-module";
    prefix "p-us-power-capabilities";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-UsPowerCapabilities {
        tlv:id 49;
        description
            "TLV [50.49]: RpdCapabilities.UsPowerCapabilities
             non-defaults: [is_rcp_readonly: True, is_readonly: True]";
        leaf MinBaseUsPowerTargetLevel {
            tlv:id 1;
            type int16;
            units "TenthdBmV";
            description
                "TLV [50.49.1]: RpdCapabilities.UsPowerCapabilities.MinBaseUsPowerTargetLevel
                 non-defaults: [is_rcp_readonly: True, is_readonly: True]";
        }

        leaf MaxBaseUsPowerTargetLevel {
            tlv:id 2;
            type int16;
            units "TenthdBmV";
            description
                "TLV [50.49.2]: RpdCapabilities.UsPowerCapabilities.MaxBaseUsPowerTargetLevel
                 non-defaults: [is_rcp_readonly: True, is_readonly: True]";
        }

        leaf MinTargetRxPowerAdjustScqam {
            tlv:id 3;
            type int16;
            units "TenthdB";
            description
                "TLV [50.49.3]: RpdCapabilities.UsPowerCapabilities.MinTargetRxPowerAdjustScqam
                 non-defaults: [is_rcp_readonly: True, is_readonly: True]";
        }

        leaf MaxTargetRxPowerAdjustScqam {
            tlv:id 4;
            type int16;
            units "TenthdB";
            description
                "TLV [50.49.4]: RpdCapabilities.UsPowerCapabilities.MaxTargetRxPowerAdjustScqam
                 non-defaults: [is_rcp_readonly: True, is_readonly: True]";
        }

        leaf MinTargetRxPowerAdjustOfdma {
            tlv:id 5;
            type int16;
            units "TenthdB";
            description
                "TLV [50.49.5]: RpdCapabilities.UsPowerCapabilities.MinTargetRxPowerAdjustOfdma
                 non-defaults: [is_rcp_readonly: True, is_readonly: True]";
        }

        leaf MaxTargetRxPowerAdjustOfdma {
            tlv:id 6;
            type int16;
            units "TenthdB";
            description
                "TLV [50.49.6]: RpdCapabilities.UsPowerCapabilities.MaxTargetRxPowerAdjustOfdma
                 non-defaults: [is_rcp_readonly: True, is_readonly: True]";
        }

        leaf MinTargetRxPowerAdjustNdr {
            tlv:id 7;
            type int16;
            units "TenthdB";
            description
                "TLV [50.49.7]: RpdCapabilities.UsPowerCapabilities.MinTargetRxPowerAdjustNdr
                 non-defaults: [is_rcp_readonly: True, is_readonly: True]";
        }

        leaf MaxTargetRxPowerAdjustNdr {
            tlv:id 8;
            type int16;
            units "TenthdB";
            description
                "TLV [50.49.8]: RpdCapabilities.UsPowerCapabilities.MaxTargetRxPowerAdjustNdr
                 non-defaults: [is_rcp_readonly: True, is_readonly: True]";
        }

    }  // g-UsPowerCapabilities grouping

}
