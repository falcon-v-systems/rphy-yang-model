module static-pw-capabilities-module {
    yang-version 1;
    /* This file is automatically generated with Falcon V System's script.
       Any change made to this file will be lost. */

    namespace "falconvsystems:r-phy-10:static-pw-capabilities-module";
    prefix "p-static-pw-capabilities";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-StaticPwCapabilities {
        tlv:id 50;
        description
            "TLV [50.50]: RpdCapabilities.StaticPwCapabilities
             non-defaults: [is_rcp_readonly: True, is_readonly: True]";
        leaf MaxFwdStaticPws {
            tlv:id 1;
            type uint16;
            description
                "TLV [50.50.1]: RpdCapabilities.StaticPwCapabilities.MaxFwdStaticPws
                 non-defaults: [is_rcp_readonly: True, is_readonly: True]";
        }

        leaf MaxRetStaticPws {
            tlv:id 2;
            type uint16;
            description
                "TLV [50.50.2]: RpdCapabilities.StaticPwCapabilities.MaxRetStaticPws
                 non-defaults: [is_rcp_readonly: True, is_readonly: True]";
        }

        leaf SupportsMptDepiPw {
            tlv:id 3;
            type boolean;
            description
                "TLV [50.50.3]: RpdCapabilities.StaticPwCapabilities.SupportsMptDepiPw
                 non-defaults: [is_rcp_readonly: True, is_readonly: True]";
        }

        leaf SupportsMpt55d1RetPw {
            tlv:id 4;
            type boolean;
            description
                "TLV [50.50.4]: RpdCapabilities.StaticPwCapabilities.SupportsMpt55d1RetPw
                 non-defaults: [is_rcp_readonly: True, is_readonly: True]";
        }

        leaf SupportsPspNdfPw {
            tlv:id 5;
            type boolean;
            description
                "TLV [50.50.5]: RpdCapabilities.StaticPwCapabilities.SupportsPspNdfPw
                 non-defaults: [is_rcp_readonly: True, is_readonly: True]";
        }

        leaf SupportsPspNdrPw {
            tlv:id 6;
            type boolean;
            description
                "TLV [50.50.6]: RpdCapabilities.StaticPwCapabilities.SupportsPspNdrPw
                 non-defaults: [is_rcp_readonly: True, is_readonly: True]";
        }

    }  // g-StaticPwCapabilities grouping

}
