module rpd-core-redundancy-capabilities-module {
    yang-version 1;
    /* This file is automatically generated with Falcon V System's script.
       Any change made to this file will be lost. */

    namespace "falconvsystems:r-phy-10:rpd-core-redundancy-capabilities-module";
    prefix "p-rpd-core-redundancy-capabilities";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-RpdCoreRedundancyCapabilities {
        tlv:id 56;
        description
            "TLV [50.56]: RpdCapabilities.RpdCoreRedundancyCapabilities
             non-defaults: [is_rcp_readonly: True, is_readonly: True]";
        leaf HandoverToBackup {
            tlv:id 1;
            type boolean;
            description
                "TLV [50.56.1]: RpdCapabilities.RpdCoreRedundancyCapabilities.HandoverToBackup
                 non-defaults: [is_rcp_readonly: True, is_readonly: True]";
        }

        leaf ConnectionStatus {
            tlv:id 2;
            type boolean;
            description
                "TLV [50.56.2]: RpdCapabilities.RpdCoreRedundancyCapabilities.ConnectionStatus
                 non-defaults: [is_rcp_readonly: True, is_readonly: True]";
        }

        leaf ReconnectFromCore {
            tlv:id 3;
            type boolean;
            description
                "TLV [50.56.3]: RpdCapabilities.RpdCoreRedundancyCapabilities.ReconnectFromCore
                 non-defaults: [is_rcp_readonly: True, is_readonly: True]";
        }

    }  // g-RpdCoreRedundancyCapabilities grouping

}
