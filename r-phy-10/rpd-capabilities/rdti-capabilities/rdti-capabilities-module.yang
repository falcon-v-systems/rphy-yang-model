module rdti-capabilities-module {
    yang-version 1;
    /* This file is automatically generated with Falcon V System's script.
       Any change made to this file will be lost. */

    namespace "falconvsystems:r-phy-10:rdti-capabilities-module";
    prefix "p-rdti-capabilities";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-RdtiCapabilities {
        tlv:id 34;
        description
            "TLV [50.34]: RpdCapabilities.RdtiCapabilities
             non-defaults: [is_rcp_readonly: True, is_readonly: True]";
        leaf NumPtpPortsPerEnetPort {
            tlv:id 1;
            type uint8;
            description
                "TLV [50.34.1]: RpdCapabilities.RdtiCapabilities.NumPtpPortsPerEnetPort
                 non-defaults: [is_rcp_readonly: True, is_readonly: True]";
        }

    }  // g-RdtiCapabilities grouping

}
