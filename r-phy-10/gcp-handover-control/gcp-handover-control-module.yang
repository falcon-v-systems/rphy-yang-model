module gcp-handover-control-module {
    yang-version 1;
    /* This file is automatically generated with Falcon V System's script.
       Any change made to this file will be lost. */

    namespace "falconvsystems:r-phy-10:gcp-handover-control-module";
    prefix "p-gcp-handover-control";

    // --- imports ---------------------------------------

    import ietf-yang-types {
        prefix "yang";
        description 
            "External YANG module.";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-GcpHandoverControl {
        tlv:id 109;
        description "TLV [109]: GcpHandoverControl";
        leaf GcpHandoverControlAction {
            tlv:id 1;
            tlv:repr uint8;
            type enumeration {
                enum noAction             { value  0; description ""; }
                enum InitiateHandover     { value  1; description ""; }
            }
            description "TLV [109.1]: GcpHandoverControl.GcpHandoverControlAction";
        }

        leaf OosCore {
            tlv:id 2;
            type yang:mac-address;
            description "TLV [109.2]: GcpHandoverControl.OosCore";
        }

        leaf NewActiveCore {
            tlv:id 3;
            type yang:mac-address;
            description "TLV [109.3]: GcpHandoverControl.NewActiveCore";
        }

        leaf L2TPv3 {
            tlv:id 4;
            tlv:repr uint8;
            type enumeration {
                enum noAction     { value  0; description ""; }
                enum tearDown     { value  1; description ""; }
                enum keepActive   { value  2; description ""; }
            }
            description "TLV [109.4]: GcpHandoverControl.L2TPv3";
        }

    }  // g-GcpHandoverControl grouping

}
