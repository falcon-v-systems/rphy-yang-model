module ndf-perf-module {
    yang-version 1;
    /* This file is automatically generated with Falcon V System's script.
       Any change made to this file will be lost. */

    namespace "falconvsystems:r-phy-10:ndf-perf-module";
    prefix "p-ndf-perf";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-NdfPerf {
        tlv:id 76;
        description
            "TLV [76]: NdfPerf
             non-defaults: [is_rcp_readonly: True, is_readonly: True]";
        leaf Index {
            // no tlv:id given
            type uint16;
            description
                "TLV [76.X]: NdfPerf.Index
                 non-defaults: [is_key: True]";
        }

        leaf outDiscards {
            tlv:id 1;
            type uint64;
            units "packets";
            description
                "TLV [76.1]: NdfPerf.outDiscards
                 non-defaults: [is_rcp_readonly: True, is_readonly: True]";
        }

        leaf outErrors {
            tlv:id 2;
            type uint64;
            units "packets";
            description
                "TLV [76.2]: NdfPerf.outErrors
                 non-defaults: [is_rcp_readonly: True, is_readonly: True]";
        }

        leaf outPackets {
            tlv:id 3;
            type uint64;
            units "packets";
            description
                "TLV [76.3]: NdfPerf.outPackets
                 non-defaults: [is_rcp_readonly: True, is_readonly: True]";
        }

        leaf discontinuityTime {
            tlv:id 4;
            type binary;
            description
                "TLV [76.4]: NdfPerf.discontinuityTime
                 non-defaults: [is_rcp_readonly: True, is_readonly: True]";
        }

        leaf operStatusNdf {
            tlv:id 5;
            tlv:repr uint8;
            type enumeration {
                enum up       { value  1; description ""; }
                enum down     { value  2; description ""; }
            }
            description
                "TLV [76.5]: NdfPerf.operStatusNdf
                 non-defaults: [is_rcp_readonly: True, is_readonly: True]";
        }

    }  // g-NdfPerf grouping

}
