module us-oob552-perf-module {
    yang-version 1;
    /* This file is automatically generated with Falcon V System's script.
       Any change made to this file will be lost. */

    namespace "falconvsystems:r-phy-10:us-oob552-perf-module";
    prefix "p-us-oob552-perf";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-UsOob552Perf {
        tlv:id 81;
        description
            "TLV [81]: UsOob552Perf
             non-defaults: [is_rcp_readonly: True, is_readonly: True]";
        leaf operStatusUsOob552 {
            tlv:id 1;
            tlv:repr uint8;
            type enumeration {
                enum up       { value  1; description ""; }
                enum down     { value  2; description ""; }
            }
            description
                "TLV [81.1]: UsOob552Perf.operStatusUsOob552
                 non-defaults: [is_rcp_readonly: True, is_readonly: True]";
        }

    }  // g-UsOob552Perf grouping

}
