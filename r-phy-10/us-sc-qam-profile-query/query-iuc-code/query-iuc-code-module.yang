module query-iuc-code-module {
    yang-version 1;
    /* This file is automatically generated with Falcon V System's script.
       Any change made to this file will be lost. */

    namespace "falconvsystems:r-phy-10:query-iuc-code-module";
    prefix "p-query-iuc-code";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-QueryIucCode {
        tlv:id 3;
        description "TLV [150.3]: UsScQamProfileQuery.QueryIucCode";
        leaf QueryScQamCode {
            tlv:id 1;
            type uint8;
            description
                "TLV [150.3.1]: UsScQamProfileQuery.QueryIucCode.QueryScQamCode";
        }

        leaf QueryScQamPreambleLen {
            tlv:id 2;
            type uint16;
            description
                "TLV [150.3.2]: UsScQamProfileQuery.QueryIucCode.QueryScQamPreambleLen";
        }

        leaf QueryScQamPreambleModType {
            tlv:id 3;
            type uint8;
            description
                "TLV [150.3.3]: UsScQamProfileQuery.QueryIucCode.QueryScQamPreambleModType";
        }

        leaf QueryScQamModulationType {
            tlv:id 4;
            type uint8;
            description
                "TLV [150.3.4]: UsScQamProfileQuery.QueryIucCode.QueryScQamModulationType";
        }

        leaf QueryScQamGuardTime {
            tlv:id 5;
            type uint8;
            description
                "TLV [150.3.5]: UsScQamProfileQuery.QueryIucCode.QueryScQamGuardTime";
        }

    }  // g-QueryIucCode grouping

}
