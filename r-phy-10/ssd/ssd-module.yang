module ssd-module {
    yang-version 1;
    /* This file is automatically generated with Falcon V System's script.
       Any change made to this file will be lost. */

    namespace "falconvsystems:r-phy-10:ssd-module";
    prefix "p-ssd";

    // --- imports ---------------------------------------

    import ietf-inet-types {
        prefix "inet";
        description 
            "External YANG module.";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-Ssd {
        tlv:id 90;
        description "TLV [90]: Ssd";
        leaf SsdServerAddress {
            tlv:id 1;
            type inet:ip-address;
            description "TLV [90.1]: Ssd.SsdServerAddress";
        }

        leaf SsdTransport {
            tlv:id 2;
            tlv:repr uint8;
            type enumeration {
                enum TFTP     { value  1; description ""; }
                enum HTTP     { value  2; description ""; }
            }
            description "TLV [90.2]: Ssd.SsdTransport";
        }

        leaf SsdFilename {
            tlv:id 3;
            type string;
            description "TLV [90.3]: Ssd.SsdFilename";
        }

        leaf SsdStatus {
            tlv:id 4;
            tlv:repr uint8;
            type enumeration {
                enum Other                { value  1; description ""; }
                enum Idle                 { value  2; description ""; }
                enum InProgress           { value  3; description ""; }
                enum CvcVerified          { value  4; description ""; }
                enum CvcRejected          { value  5; description ""; }
                enum CodeFileVerified     { value  6; description ""; }
                enum CodeFileRejected     { value  7; description ""; }
            }
            description "TLV [90.4]: Ssd.SsdStatus";
        }

        leaf SsdControl {
            tlv:id 5;
            tlv:repr uint8;
            type enumeration {
                enum Other        { value  1; description ""; }
                enum StartSsu     { value  2; description ""; }
                enum AbortSsu     { value  3; description ""; }
            }
            description "TLV [90.5]: Ssd.SsdControl";
        }

        leaf SsdManufCvcChain {
            tlv:id 6;
            type binary;
            description "TLV [90.6]: Ssd.SsdManufCvcChain";
        }

        leaf SsdCosignerCvcChain {
            tlv:id 7;
            type binary;
            description "TLV [90.7]: Ssd.SsdCosignerCvcChain";
        }

        leaf SwImageIndex {
            tlv:id 8;
            type uint8;
            description "TLV [90.8]: Ssd.SwImageIndex";
        }

    }  // g-Ssd grouping

}
