module general-notification-module {
    yang-version 1;
    /* This file is automatically generated with Falcon V System's script.
       Any change made to this file will be lost. */

    namespace "falconvsystems:r-phy-10:general-notification-module";
    prefix "p-general-notification";

    // --- imports ---------------------------------------

    import ietf-inet-types {
        prefix "inet";
        /*  External YANG module. */
    }

    import ietf-yang-types {
        prefix "yang";
        /*  External YANG module. */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-GeneralNotification {
        tlv:id 86;
        description "TLV [86]: GeneralNotification";

        leaf NotificationType {
            tlv:id 1;
            tlv:repr uint8;
            type enumeration {
                enum StartUpNotification            { value  1; description ""; }
                enum RedirectResultNotification     { value  2; description ""; }
                enum PtpResultNotification          { value  3; description ""; }
                enum AuxCoreResultNotification      { value  4; description ""; }
                enum TimeOutNotification            { value  5; description ""; }
                enum RpdOperationalNotification     { value  6; description ""; }
                enum ReconnectNotification          { value  7; description ""; }
                enum AuxCoreGcpStatusNotification   { value  8; description ""; }
                enum ChannelUcdRefreshRequest       { value  9; description ""; }
            }
            description
                "TLV [86.1]: GeneralNotification.NotificationType
                 non-defaults: [is_rcp_readonly: True, is_readonly: True]";
        }

        leaf RpdRedirectResult {
            tlv:id 2;
            tlv:repr uint8;
            type enumeration {
                enum Success    { value  0; description ""; }
                enum Fail       { value  1; description ""; }
            }
            description
                "TLV [86.2]: GeneralNotification.RpdRedirectResult
                 non-defaults: [is_rcp_readonly: True, is_readonly: True]";
        }

        leaf RpdRedirectIpAddress {
            tlv:id 3;
            type inet:ip-address;
            description
                "TLV [86.3]: GeneralNotification.RpdRedirectIpAddress
                 non-defaults: [is_rcp_readonly: True, is_readonly: True]";
        }

        leaf PtpRpdEnetPortIndex {
            tlv:id 4;
            type uint8;
            description
                "TLV [86.4]: GeneralNotification.PtpRpdEnetPortIndex
                 non-defaults: [is_rcp_readonly: True, is_readonly: True]";
        }

        leaf PtpResult {
            tlv:id 5;
            tlv:repr uint8;
            type enumeration {
                enum FreeRunning        { value  0; description ""; }
                enum Acquiring          { value  1; description ""; }
                enum HoldoverOutOfSpec  { value  2; description ""; }
                enum HoldoverWithinSpec { value  3; description ""; }
                enum Synchronized       { value  4; description ""; }
            }
            description
                "TLV [86.5]: GeneralNotification.PtpResult
                 non-defaults: [is_rcp_readonly: True, is_readonly: True]";
        }

        leaf AuxCoreResult {
            tlv:id 6;
            tlv:repr uint8;
            type enumeration {
                enum Operational    { value  0; description ""; }
                enum CoreNotActive  { value  1; description ""; }
                enum Failure        { value  2; description ""; }
            }
            description
                "TLV [86.6]: GeneralNotification.AuxCoreResult
                 non-defaults: [is_rcp_readonly: True, is_readonly: True]";
        }

        leaf AuxCoreIpAddress {
            tlv:id 7;
            type inet:ip-address;
            description
                "TLV [86.7]: GeneralNotification.AuxCoreIpAddress
                 non-defaults: [is_rcp_readonly: True, is_readonly: True]";
        }

        leaf AuxCoreFailureType {
            tlv:id 8;
            tlv:repr uint8;
            type enumeration {
                enum Authentication                 { value  1; description ""; }
                enum OtherActivePrincipalCore       { value  2; description ""; }
                enum WaitRARetriesExceeded          { value  3; description ""; }
                enum WaitConfigRetriesExceeded      { value  4; description ""; }
                enum InitialTcpConnectionFailure    { value  5; description ""; }
                enum GeneralTcpFailure              { value  6; description ""; }
                enum GcpKeepaliveTimeout            { value  7; description ""; }
                enum WaitOperationalRetriesExceeded { value  8; description ""; }
            }
            description
                "TLV [86.8]: GeneralNotification.AuxCoreFailureType
                 non-defaults: [is_rcp_readonly: True, is_readonly: True]";
        }

        leaf SpecificTimeOut {
            tlv:id 9;
            tlv:repr uint8;
            type enumeration {
                enum NoRexConfigAfterIraPrin    { value  1; description ""; }
                enum WaitForOperationalPrin     { value  2; description ""; }
                enum NoRexConfigAfterIraAux     { value  3; description ""; }
                enum WaitForOperationalAux      { value  4; description ""; }
                enum LocalPtpSync               { value  5; description ""; }
            }
            description
                "TLV [86.9]: GeneralNotification.SpecificTimeOut
                 non-defaults: [is_rcp_readonly: True, is_readonly: True]";
        }

        leaf CoreTimedOutIpAddress {
            tlv:id 10;
            type inet:ip-address;
            description
                "TLV [86.10]: GeneralNotification.CoreTimedOutIpAddress
                 non-defaults: [is_rcp_readonly: True, is_readonly: True]";
        }

        leaf PtpRpdPtpPortIndex {
            tlv:id 11;
            type uint8;
            description
                "TLV [86.11]: GeneralNotification.PtpRpdPtpPortIndex
                 non-defaults: [is_rcp_readonly: True, is_readonly: True]";
        }

        leaf PtpClockSource {
            tlv:id 12;
            tlv:repr uint8;
            type enumeration {
                enum PrimaryClockSource     { value  0; description ""; }
                enum AlternateClockSource   { value  1; description ""; }
            }
            description
                "TLV [86.12]: GeneralNotification.PtpClockSource
                 non-defaults: [is_rcp_readonly: True, is_readonly: True]";
        }

        leaf AuxCoreGcpConnectionStatus {
            tlv:id 13;
            tlv:repr uint8;
            type enumeration {
                enum NotConnected   { value  0; description ""; }
                enum Connected      { value  1; description ""; }
                enum Reconnecting   { value  2; description ""; }
            }
            description
                "TLV [86.13]: GeneralNotification.AuxCoreGcpConnectionStatus
                 non-defaults: [is_rcp_readonly: True, is_readonly: True]";
        }

        leaf AuxCoreId {
            tlv:id 14;
            type yang:mac-address;
            description
                "TLV [86.14]: GeneralNotification.AuxCoreId
                 non-defaults: [is_rcp_readonly: True, is_readonly: True]";
        }

        leaf SsdFailureType {
            tlv:id 15;
            type uint32;
            description
                "TLV [86.15]: GeneralNotification.SsdFailureType
                 non-defaults: [is_rcp_readonly: True, is_readonly: True]";
        }

    }  // g-GeneralNotification grouping

}
