module fft-module {
    yang-version 1;
    /* This file is automatically generated with Falcon V System's script.
       Any change made to this file will be lost. */

    namespace "falconvsystems:r-phy-10:fft-module";
    prefix "p-fft";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-Fft {
        tlv:id 99;
        description
            "TLV [99]: Fft
             non-defaults: [is_readonly: True]";

        leaf Sid {
            tlv:id 1;
            type uint16;
            description
                "TLV [99.1]: Fft.Sid
                 non-defaults: [is_readonly: True]";
        }

        leaf Freq {
            tlv:id 2;
            type uint32;
            description
                "TLV [99.2]: Fft.Freq
                 non-defaults: [is_readonly: True]";
        }

        leaf Iuc {
            tlv:id 3;
            type uint8;
            description "TLV [99.3]: Fft.Iuc";
        }

        leaf Size {
            tlv:id 4;
            type uint32;
            description "TLV [99.4]: Fft.Size";
        }

        leaf Mode {
            tlv:id 5;
            type uint16;
            description "TLV [99.5]: Fft.Mode";
        }

    }  // g-Fft grouping

}
