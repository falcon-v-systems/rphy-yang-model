module rf-port-module {
    yang-version 1;
    /* This file is automatically generated with Falcon V System's script.
       Any change made to this file will be lost. */

    namespace "falconvsystems:r-phy-10:rf-port-module";
    prefix "p-rf-port";

    // --- imports ---------------------------------------

    import ds-rf-port-module {
        prefix "p-ds-rf-port";
        /*  File path: rex/rf-port/ds-rf-port/ds-rf-port-module.yang
            https://github.com/falcon-v-systems/rphy-yang-model/blob/master/r-phy-10/rex/rf-port/ds-rf-port/ds-rf-port-module.yang */
    }

    import ds-rf-port-perf-module {
        prefix "p-ds-rf-port-perf";
        /*  File path: rex/rf-port/ds-rf-port-perf-module.yang
            https://github.com/falcon-v-systems/rphy-yang-model/blob/master/r-phy-10/rex/rf-port/ds-rf-port-perf-module.yang */
    }

    import rf-port-selector-module {
        prefix "p-rf-port-selector";
        /*  File path: rex/rf-port/rf-port-selector-module.yang
            https://github.com/falcon-v-systems/rphy-yang-model/blob/master/r-phy-10/rex/rf-port/rf-port-selector-module.yang */
    }

    import tlv-extension {
        prefix "tlv";
        /*  Falcon's Yang extension for TLV attributes. */
    }

    import us-rf-port-module {
        prefix "p-us-rf-port";
        /*  File path: rex/rf-port/us-rf-port/us-rf-port-module.yang
            https://github.com/falcon-v-systems/rphy-yang-model/blob/master/r-phy-10/rex/rf-port/us-rf-port/us-rf-port-module.yang */
    }

    import us-rf-port-perf-module {
        prefix "p-us-rf-port-perf";
        /*  File path: rex/rf-port/us-rf-port-perf-module.yang
            https://github.com/falcon-v-systems/rphy-yang-model/blob/master/r-phy-10/rex/rf-port/us-rf-port-perf-module.yang */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-RfPort {
        tlv:id 17;
        description "TLV [17]: RfPort";

        container RfPortSelector {
            tlv:id 13;
            description "TLV [13]: RfPortSelector";
            uses "p-rf-port-selector:g-RfPortSelector";
        }

        choice port-topic {
            case DsRfPort {
                list DsRfPort {
                    tlv:id 61;
                    key "PortIndex";
                    description "TLV [61]: DsRfPort";
                    uses "p-ds-rf-port:g-DsRfPort";
                }
            }

            case DsRfPortPerf {
                list DsRfPortPerf {
                    tlv:id 71;
                    key "PortIndex";
                    description
                        "TLV [71]: DsRfPortPerf
                         non-defaults: [is_rcp_readonly: True, is_readonly: True]";
                    uses "p-ds-rf-port-perf:g-DsRfPortPerf";
                }
            }

            case UsRfPortPerf {
                list UsRfPortPerf {
                    tlv:id 77;
                    key "PortIndex";
                    description
                        "TLV [77]: UsRfPortPerf
                         non-defaults: [is_rcp_readonly: True, is_readonly: True]";
                    uses "p-us-rf-port-perf:g-UsRfPortPerf";
                }
            }

            case UsRfPort {
                list UsRfPort {
                    tlv:id 98;
                    key "PortIndex";
                    description "TLV [98]: UsRfPort";
                    uses "p-us-rf-port:g-UsRfPort";
                }
            }

            description 
                "The choice statement defines a set of alternatives,
                 only one of which may exist at any one time.";
        }
    }  // g-RfPort grouping

}
