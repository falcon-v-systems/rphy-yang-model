module us-rf-port-perf-module {
    yang-version 1;
    /* This file is automatically generated with Falcon V System's script.
       Any change made to this file will be lost. */

    namespace "falconvsystems:r-phy-10:us-rf-port-perf-module";
    prefix "p-us-rf-port-perf";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UsRfPortPerf {
        tlv:id 77;
        description
            "TLV [77]: UsRfPortPerf
             non-defaults: [is_rcp_readonly: True, is_readonly: True]";

        leaf PortIndex {
            // no tlv:id given
            type uint16;
            description
                "TLV [77.X]: UsRfPortPerf.PortIndex
                 non-defaults: [is_key: True]";
        }

        leaf operStatusUsRfPort {
            tlv:id 1;
            tlv:repr uint8;
            type enumeration {
                enum up     { value  1; description ""; }
                enum down   { value  2; description ""; }
            }
            description
                "TLV [77.1]: UsRfPortPerf.operStatusUsRfPort
                 non-defaults: [is_rcp_readonly: True, is_readonly: True]";
        }

    }  // g-UsRfPortPerf grouping

}
