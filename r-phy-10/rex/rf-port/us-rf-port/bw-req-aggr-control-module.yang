module bw-req-aggr-control-module {
    yang-version 1;
    /* This file is automatically generated with Falcon V System's script.
       Any change made to this file will be lost. */

    namespace "falconvsystems:r-phy-10:bw-req-aggr-control-module";
    prefix "p-bw-req-aggr-control";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-BwReqAggrControl {
        tlv:id 2;
        description "TLV [98.2]: UsRfPort.BwReqAggrControl";

        leaf MaxReqBlockEnqTimeout {
            tlv:id 1;
            type uint16;
            units "microseconds";
            description
                "TLV [98.2.1]: UsRfPort.BwReqAggrControl.MaxReqBlockEnqTimeout";
        }

        leaf MaxReqBlockEnqNumber {
            tlv:id 2;
            type uint8;
            description "TLV [98.2.2]: UsRfPort.BwReqAggrControl.MaxReqBlockEnqNumber";
        }

    }  // g-BwReqAggrControl grouping

}
