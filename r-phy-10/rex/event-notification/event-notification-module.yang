module event-notification-module {
    yang-version 1;
    /* This file is automatically generated with Falcon V System's script.
       Any change made to this file will be lost. */

    namespace "falconvsystems:r-phy-10:event-notification-module";
    prefix "p-event-notification";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-EventNotification {
        tlv:id 85;
        description "TLV [85]: EventNotification";

        leaf RpdEvLogIndex {
            tlv:id 1;
            type uint32;
            description
                "TLV [85.1]: EventNotification.RpdEvLogIndex
                 non-defaults: [is_rcp_readonly: True, is_readonly: True]";
        }

        leaf PendingOrLocalLog {
            tlv:id 2;
            type boolean;
            description
                "TLV [85.2]: EventNotification.PendingOrLocalLog
                 non-defaults: [is_rcp_readonly: True, is_readonly: True]";
        }

        leaf EvFirstTime {
            tlv:id 3;
            type binary;
            description
                "TLV [85.3]: EventNotification.EvFirstTime
                 non-defaults: [is_rcp_readonly: True, is_readonly: True]";
        }

        leaf EvLastTime {
            tlv:id 4;
            type binary;
            description
                "TLV [85.4]: EventNotification.EvLastTime
                 non-defaults: [is_rcp_readonly: True, is_readonly: True]";
        }

        leaf EvCounts {
            tlv:id 5;
            type uint32;
            description
                "TLV [85.5]: EventNotification.EvCounts
                 non-defaults: [is_rcp_readonly: True, is_readonly: True]";
        }

        leaf EvLevel {
            tlv:id 6;
            tlv:repr uint8;
            type enumeration {
                enum emergency      { value  1; description ""; }
                enum alert          { value  2; description ""; }
                enum critical       { value  3; description ""; }
                enum error          { value  4; description ""; }
                enum warning        { value  5; description ""; }
                enum notice         { value  6; description ""; }
                enum information    { value  7; description ""; }
                enum debug          { value  8; description ""; }
            }
            description
                "TLV [85.6]: EventNotification.EvLevel
                 non-defaults: [is_rcp_readonly: True, is_readonly: True]";
        }

        leaf EvId {
            tlv:id 7;
            type uint32;
            description
                "TLV [85.7]: EventNotification.EvId
                 non-defaults: [is_rcp_readonly: True, is_readonly: True]";
        }

        leaf EvString {
            tlv:id 8;
            type string;
            description
                "TLV [85.8]: EventNotification.EvString
                 non-defaults: [is_rcp_readonly: True, is_readonly: True]";
        }

    }  // g-EventNotification grouping

}
