module rpd-info-module {
    yang-version 1;
    /* This file is automatically generated with Falcon V System's script.
       Any change made to this file will be lost. */

    namespace "falconvsystems:r-phy-10:rpd-info-module";
    prefix "p-rpd-info";

    // --- imports ---------------------------------------

    import crash-data-file-status-module {
        prefix "p-crash-data-file-status";
        /*  File path: rex/rpd-info/crash-data-file-status-module.yang
            https://github.com/falcon-v-systems/rphy-yang-model/blob/master/r-phy-10/rex/rpd-info/crash-data-file-status-module.yang */
    }

    import depi-mcast-session-module {
        prefix "p-depi-mcast-session";
        /*  File path: rex/rpd-info/depi-mcast-session-module.yang
            https://github.com/falcon-v-systems/rphy-yang-model/blob/master/r-phy-10/rex/rpd-info/depi-mcast-session-module.yang */
    }

    import diagnostic-status-module {
        prefix "p-diagnostic-status";
        /*  File path: rex/rpd-info/diagnostic-status-module.yang
            https://github.com/falcon-v-systems/rphy-yang-model/blob/master/r-phy-10/rex/rpd-info/diagnostic-status-module.yang */
    }

    import entity-module {
        prefix "p-entity";
        /*  File path: rex/rpd-info/entity-module.yang
            https://github.com/falcon-v-systems/rphy-yang-model/blob/master/r-phy-10/rex/rpd-info/entity-module.yang */
    }

    import ext-sw-image-support-module {
        prefix "p-ext-sw-image-support";
        /*  File path: rex/rpd-info/ext-sw-image-support-module.yang
            https://github.com/falcon-v-systems/rphy-yang-model/blob/master/r-phy-10/rex/rpd-info/ext-sw-image-support-module.yang */
    }

    import host-resources-storage-module {
        prefix "p-host-resources-storage";
        /*  File path: rex/rpd-info/host-resources-storage-module.yang
            https://github.com/falcon-v-systems/rphy-yang-model/blob/master/r-phy-10/rex/rpd-info/host-resources-storage-module.yang */
    }

    import host-resources-sw-run-module {
        prefix "p-host-resources-sw-run";
        /*  File path: rex/rpd-info/host-resources-sw-run-module.yang
            https://github.com/falcon-v-systems/rphy-yang-model/blob/master/r-phy-10/rex/rpd-info/host-resources-sw-run-module.yang */
    }

    import host-resources-system-module {
        prefix "p-host-resources-system";
        /*  File path: rex/rpd-info/host-resources-system-module.yang
            https://github.com/falcon-v-systems/rphy-yang-model/blob/master/r-phy-10/rex/rpd-info/host-resources-system-module.yang */
    }

    import icmp-msg-stats-module {
        prefix "p-icmp-msg-stats";
        /*  File path: rex/rpd-info/icmp-msg-stats-module.yang
            https://github.com/falcon-v-systems/rphy-yang-model/blob/master/r-phy-10/rex/rpd-info/icmp-msg-stats-module.yang */
    }

    import ieee8021x-pae-supplicant-status-module {
        prefix "p-ieee8021x-pae-supplicant-status";
        /*  File path: rex/rpd-info/ieee8021x-pae-supplicant-status-module.yang
            https://github.com/falcon-v-systems/rphy-yang-model/blob/master/r-phy-10/rex/rpd-info/ieee8021x-pae-supplicant-status-module.yang */
    }

    import if-enet-module {
        prefix "p-if-enet";
        /*  File path: rex/rpd-info/if-enet-module.yang
            https://github.com/falcon-v-systems/rphy-yang-model/blob/master/r-phy-10/rex/rpd-info/if-enet-module.yang */
    }

    import if-enet-stats-module {
        prefix "p-if-enet-stats";
        /*  File path: rex/rpd-info/if-enet-stats-module.yang
            https://github.com/falcon-v-systems/rphy-yang-model/blob/master/r-phy-10/rex/rpd-info/if-enet-stats-module.yang */
    }

    import ip-address-module {
        prefix "p-ip-address";
        /*  File path: rex/rpd-info/ip-address-module.yang
            https://github.com/falcon-v-systems/rphy-yang-model/blob/master/r-phy-10/rex/rpd-info/ip-address-module.yang */
    }

    import ip-default-router-module {
        prefix "p-ip-default-router";
        /*  File path: rex/rpd-info/ip-default-router-module.yang
            https://github.com/falcon-v-systems/rphy-yang-model/blob/master/r-phy-10/rex/rpd-info/ip-default-router-module.yang */
    }

    import ip-if-stats-module {
        prefix "p-ip-if-stats";
        /*  File path: rex/rpd-info/ip-if-stats-module.yang
            https://github.com/falcon-v-systems/rphy-yang-model/blob/master/r-phy-10/rex/rpd-info/ip-if-stats-module.yang */
    }

    import ip-interface-grp-module {
        prefix "p-ip-interface-grp";
        /*  File path: rex/rpd-info/ip-interface-grp-module.yang
            https://github.com/falcon-v-systems/rphy-yang-model/blob/master/r-phy-10/rex/rpd-info/ip-interface-grp-module.yang */
    }

    import ip-net-to-physical-module {
        prefix "p-ip-net-to-physical";
        /*  File path: rex/rpd-info/ip-net-to-physical-module.yang
            https://github.com/falcon-v-systems/rphy-yang-model/blob/master/r-phy-10/rex/rpd-info/ip-net-to-physical-module.yang */
    }

    import ipv4-interface-module {
        prefix "p-ipv4-interface";
        /*  File path: rex/rpd-info/ipv4-interface-module.yang
            https://github.com/falcon-v-systems/rphy-yang-model/blob/master/r-phy-10/rex/rpd-info/ipv4-interface-module.yang */
    }

    import ipv6-interface-module {
        prefix "p-ipv6-interface";
        /*  File path: rex/rpd-info/ipv6-interface-module.yang
            https://github.com/falcon-v-systems/rphy-yang-model/blob/master/r-phy-10/rex/rpd-info/ipv6-interface-module.yang */
    }

    import rpd-aaa-server-auth-module {
        prefix "p-rpd-aaa-server-auth";
        /*  File path: rex/rpd-info/rpd-aaa-server-auth-module.yang
            https://github.com/falcon-v-systems/rphy-yang-model/blob/master/r-phy-10/rex/rpd-info/rpd-aaa-server-auth-module.yang */
    }

    import rpd-ccap-core-auth-module {
        prefix "p-rpd-ccap-core-auth";
        /*  File path: rex/rpd-info/rpd-ccap-core-auth-module.yang
            https://github.com/falcon-v-systems/rphy-yang-model/blob/master/r-phy-10/rex/rpd-info/rpd-ccap-core-auth-module.yang */
    }

    import rpd-cert-module {
        prefix "p-rpd-cert";
        /*  File path: rex/rpd-info/rpd-cert-module.yang
            https://github.com/falcon-v-systems/rphy-yang-model/blob/master/r-phy-10/rex/rpd-info/rpd-cert-module.yang */
    }

    import rpd-enet-to-core-entity-map-module {
        prefix "p-rpd-enet-to-core-entity-map";
        /*  File path: rex/rpd-info/rpd-enet-to-core-entity-map-module.yang
            https://github.com/falcon-v-systems/rphy-yang-model/blob/master/r-phy-10/rex/rpd-info/rpd-enet-to-core-entity-map-module.yang */
    }

    import rpd-l2tp-session-info-module {
        prefix "p-rpd-l2tp-session-info";
        /*  File path: rex/rpd-info/rpd-l2tp-session-info/rpd-l2tp-session-info-module.yang
            https://github.com/falcon-v-systems/rphy-yang-model/blob/master/r-phy-10/rex/rpd-info/rpd-l2tp-session-info/rpd-l2tp-session-info-module.yang */
    }

    import rpd-ptp-status-module {
        prefix "p-rpd-ptp-status";
        /*  File path: rex/rpd-info/rpd-ptp-status/rpd-ptp-status-module.yang
            https://github.com/falcon-v-systems/rphy-yang-model/blob/master/r-phy-10/rex/rpd-info/rpd-ptp-status/rpd-ptp-status-module.yang */
    }

    import rpd-sys-module {
        prefix "p-rpd-sys";
        /*  File path: rex/rpd-info/rpd-sys-module.yang
            https://github.com/falcon-v-systems/rphy-yang-model/blob/master/r-phy-10/rex/rpd-info/rpd-sys-module.yang */
    }

    import sensor-module {
        prefix "p-sensor";
        /*  File path: rex/rpd-info/sensor-module.yang
            https://github.com/falcon-v-systems/rphy-yang-model/blob/master/r-phy-10/rex/rpd-info/sensor-module.yang */
    }

    import sfp-plus-status-module {
        prefix "p-sfp-plus-status";
        /*  File path: rex/rpd-info/sfp-plus-status-module.yang
            https://github.com/falcon-v-systems/rphy-yang-model/blob/master/r-phy-10/rex/rpd-info/sfp-plus-status-module.yang */
    }

    import tlv-extension {
        prefix "tlv";
        /*  Falcon's Yang extension for TLV attributes. */
    }

    import trust-anchor-cert-module {
        prefix "p-trust-anchor-cert";
        /*  File path: rex/rpd-info/trust-anchor-cert-module.yang
            https://github.com/falcon-v-systems/rphy-yang-model/blob/master/r-phy-10/rex/rpd-info/trust-anchor-cert-module.yang */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-RpdInfo {
        tlv:id 100;
        description "TLV [100]: RpdInfo";

        container RpdSys {
            tlv:id 1;
            description "TLV [100.1]: RpdInfo.RpdSys";
            uses "p-rpd-sys:g-RpdSys";
        }

        list RpdL2tpSessionInfo {
            tlv:id 2;
            key "SessionIpAddrType CcapLcceIpAddress RpdLcceIpAddr Direction L2tpSessionId";
            description "TLV [100.2]: RpdInfo.RpdL2tpSessionInfo";
            uses "p-rpd-l2tp-session-info:g-RpdL2tpSessionInfo";
        }

        container DiagnosticStatus {
            tlv:id 4;
            description "TLV [100.4]: RpdInfo.DiagnosticStatus";
            uses "p-diagnostic-status:g-DiagnosticStatus";
        }

        list DepiMcastSession {
            tlv:id 5;
            key "IpAddrType GroupIpAddr SrcIpAddr L2tpSessionId";
            description "TLV [100.5]: RpdInfo.DepiMcastSession";
            uses "p-depi-mcast-session:g-DepiMcastSession";
        }

        list Entity {
            tlv:id 6;
            key "EntityIndex";
            description "TLV [100.6]: RpdInfo.Entity";
            uses "p-entity:g-Entity";
        }

        list Sensor {
            tlv:id 7;
            key "EntityIndex";
            description "TLV [100.7]: RpdInfo.Sensor";
            uses "p-sensor:g-Sensor";
        }

        list IfEnet {
            tlv:id 8;
            key "EnetPortIndex";
            description "TLV [100.8]: RpdInfo.IfEnet";
            uses "p-if-enet:g-IfEnet";
        }

        list IfEnetStats {
            tlv:id 9;
            key "EnetPortIndex";
            description "TLV [100.9]: RpdInfo.IfEnetStats";
            uses "p-if-enet-stats:g-IfEnetStats";
        }

        list RpdEnetToCoreEntityMap {
            tlv:id 10;
            key "EnetPortIndex";
            description "TLV [100.10]: RpdInfo.RpdEnetToCoreEntityMap";
            uses "p-rpd-enet-to-core-entity-map:g-RpdEnetToCoreEntityMap";
        }

        container IpInterfaceGrp {
            tlv:id 11;
            description "TLV [100.11]: RpdInfo.IpInterfaceGrp";
            uses "p-ip-interface-grp:g-IpInterfaceGrp";
        }

        list Ipv4Interface {
            tlv:id 12;
            key "EnetPortIndex";
            description "TLV [100.12]: RpdInfo.Ipv4Interface";
            uses "p-ipv4-interface:g-Ipv4Interface";
        }

        list Ipv6Interface {
            tlv:id 13;
            key "EnetPortIndex";
            description "TLV [100.13]: RpdInfo.Ipv6Interface";
            uses "p-ipv6-interface:g-Ipv6Interface";
        }

        list IpIfStats {
            tlv:id 14;
            key "IpVersion EnetPortIndex";
            description "TLV [100.14]: RpdInfo.IpIfStats";
            uses "p-ip-if-stats:g-IpIfStats";
        }

        list IpAddress {
            tlv:id 15;
            key "AddrType IpAddress";
            description "TLV [100.15]: RpdInfo.IpAddress";
            uses "p-ip-address:g-IpAddress";
        }

        list IpNetToPhysical {
            tlv:id 16;
            key "EnetPortIndex AddrType IpAddress";
            description "TLV [100.16]: RpdInfo.IpNetToPhysical";
            uses "p-ip-net-to-physical:g-IpNetToPhysical";
        }

        list IpDefaultRouter {
            tlv:id 17;
            key "AddrType IpAddress EnetPortIndex";
            description "TLV [100.17]: RpdInfo.IpDefaultRouter";
            uses "p-ip-default-router:g-IpDefaultRouter";
        }

        list SfpPlusStatus {
            tlv:id 18;
            key "EnetPortIndex";
            description "TLV [100.18]: RpdInfo.SfpPlusStatus";
            uses "p-sfp-plus-status:g-SfpPlusStatus";
        }

        list IcmpMsgStats {
            tlv:id 19;
            key "IpVersion Type";
            description "TLV [100.19]: RpdInfo.IcmpMsgStats";
            uses "p-icmp-msg-stats:g-IcmpMsgStats";
        }

        list CrashDataFileStatus {
            tlv:id 20;
            key "Index";
            description "TLV [100.20]: RpdInfo.CrashDataFileStatus";
            uses "p-crash-data-file-status:g-CrashDataFileStatus";
        }

        container HostResourcesSystem {
            tlv:id 21;
            description "TLV [100.21]: RpdInfo.HostResourcesSystem";
            uses "p-host-resources-system:g-HostResourcesSystem";
        }

        list HostResourcesStorage {
            tlv:id 22;
            key "Index";
            description "TLV [100.22]: RpdInfo.HostResourcesStorage";
            uses "p-host-resources-storage:g-HostResourcesStorage";
        }

        list HostResourcesSwRun {
            tlv:id 23;
            key "Index";
            description "TLV [100.23]: RpdInfo.HostResourcesSwRun";
            uses "p-host-resources-sw-run:g-HostResourcesSwRun";
        }

        container RpdPtpStatus {
            tlv:id 24;
            description "TLV [100.24]: RpdInfo.RpdPtpStatus";
            uses "p-rpd-ptp-status:g-RpdPtpStatus";
        }

        list ExtSwImageSupport {
            tlv:id 25;
            key "SwImageIndex";
            description "TLV [100.25]: RpdInfo.ExtSwImageSupport";
            uses "p-ext-sw-image-support:g-ExtSwImageSupport";
        }

        container RpdCert {
            tlv:id 26;
            description "TLV [100.26]: RpdInfo.RpdCert";
            uses "p-rpd-cert:g-RpdCert";
        }

        list TrustAnchorCert {
            tlv:id 27;
            key "Index";
            description "TLV [100.27]: RpdInfo.TrustAnchorCert";
            uses "p-trust-anchor-cert:g-TrustAnchorCert";
        }

        container RpdAaaServerAuth {
            tlv:id 28;
            description "TLV [100.28]: RpdInfo.RpdAaaServerAuth";
            uses "p-rpd-aaa-server-auth:g-RpdAaaServerAuth";
        }

        container RpdCcapCoreAuth {
            tlv:id 29;
            description "TLV [100.29]: RpdInfo.RpdCcapCoreAuth";
            uses "p-rpd-ccap-core-auth:g-RpdCcapCoreAuth";
        }

        list Ieee8021xPaeSupplicantStatus {
            tlv:id 30;
            key "PortNumber";
            description "TLV [100.30]: RpdInfo.Ieee8021xPaeSupplicantStatus";
            uses "p-ieee8021x-pae-supplicant-status:g-Ieee8021xPaeSupplicantStatus";
        }

    }  // g-RpdInfo grouping

}
