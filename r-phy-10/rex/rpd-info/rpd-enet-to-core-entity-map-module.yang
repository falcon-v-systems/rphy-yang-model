module rpd-enet-to-core-entity-map-module {
    yang-version 1;
    /* This file is automatically generated with Falcon V System's script.
       Any change made to this file will be lost. */

    namespace "falconvsystems:r-phy-10:rpd-enet-to-core-entity-map-module";
    prefix "p-rpd-enet-to-core-entity-map";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-RpdEnetToCoreEntityMap {
        tlv:id 10;
        description "TLV [100.10]: RpdInfo.RpdEnetToCoreEntityMap";

        leaf EnetPortIndex {
            tlv:id 1;
            type uint8;
            description
                "TLV [100.10.1]: RpdInfo.RpdEnetToCoreEntityMap.EnetPortIndex
                 non-defaults: [is_key: True]";
        }

        leaf EntityIndex {
            tlv:id 2;
            type uint32;
            description "TLV [100.10.2]: RpdInfo.RpdEnetToCoreEntityMap.EntityIndex";
        }

    }  // g-RpdEnetToCoreEntityMap grouping

}
