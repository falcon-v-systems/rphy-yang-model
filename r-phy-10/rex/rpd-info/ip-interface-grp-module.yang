module ip-interface-grp-module {
    yang-version 1;
    /* This file is automatically generated with Falcon V System's script.
       Any change made to this file will be lost. */

    namespace "falconvsystems:r-phy-10:ip-interface-grp-module";
    prefix "p-ip-interface-grp";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-IpInterfaceGrp {
        tlv:id 11;
        description "TLV [100.11]: RpdInfo.IpInterfaceGrp";

        leaf Ipv4InterfaceTableLastChange {
            tlv:id 1;
            type uint32;
            description
                "TLV [100.11.1]: RpdInfo.IpInterfaceGrp.Ipv4InterfaceTableLastChange";
        }

        leaf Ipv6InterfaceTableLastChange {
            tlv:id 2;
            type uint32;
            description
                "TLV [100.11.2]: RpdInfo.IpInterfaceGrp.Ipv6InterfaceTableLastChange";
        }

        leaf IpIfStatsTableLastChange {
            tlv:id 3;
            type uint32;
            description
                "TLV [100.11.3]: RpdInfo.IpInterfaceGrp.IpIfStatsTableLastChange";
        }

        leaf Ipv4DefaultTTL {
            tlv:id 5;
            type uint32;
            description "TLV [100.11.5]: RpdInfo.IpInterfaceGrp.Ipv4DefaultTTL";
        }

        leaf Ipv6DefaultHopLimit {
            tlv:id 8;
            type uint32;
            description "TLV [100.11.8]: RpdInfo.IpInterfaceGrp.Ipv6DefaultHopLimit";
        }

    }  // g-IpInterfaceGrp grouping

}
