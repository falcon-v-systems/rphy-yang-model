module crash-data-file-status-module {
    yang-version 1;
    /* This file is automatically generated with Falcon V System's script.
       Any change made to this file will be lost. */

    namespace "falconvsystems:r-phy-10:crash-data-file-status-module";
    prefix "p-crash-data-file-status";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-CrashDataFileStatus {
        tlv:id 20;
        description "TLV [100.20]: RpdInfo.CrashDataFileStatus";

        leaf Index {
            tlv:id 1;
            type uint8;
            description
                "TLV [100.20.1]: RpdInfo.CrashDataFileStatus.Index
                 non-defaults: [is_key: True]";
        }

        leaf Filename {
            tlv:id 2;
            type string;
            description "TLV [100.20.2]: RpdInfo.CrashDataFileStatus.Filename";
        }

        leaf FileStatus {
            tlv:id 3;
            tlv:repr uint8;
            type enumeration {
                enum other              { value  1; description ""; }
                enum availableForUpload { value  2; description ""; }
                enum uploadInProgress   { value  3; description ""; }
                enum uploadCompleted    { value  4; description ""; }
                enum uploadPending      { value  5; description ""; }
                enum uploadCancelled    { value  6; description ""; }
                enum error              { value  7; description ""; }
            }
            description "TLV [100.20.3]: RpdInfo.CrashDataFileStatus.FileStatus";
        }

    }  // g-CrashDataFileStatus grouping

}
