module diagnostic-status-module {
    yang-version 1;
    /* This file is automatically generated with Falcon V System's script.
       Any change made to this file will be lost. */

    namespace "falconvsystems:r-phy-10:diagnostic-status-module";
    prefix "p-diagnostic-status";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-DiagnosticStatus {
        tlv:id 4;
        description "TLV [100.4]: RpdInfo.DiagnosticStatus";

        leaf ProbableCause {
            tlv:id 1;
            type string;
            description "TLV [100.4.1]: RpdInfo.DiagnosticStatus.ProbableCause";
        }

        leaf AdditionalText {
            tlv:id 2;
            type string;
            description "TLV [100.4.2]: RpdInfo.DiagnosticStatus.AdditionalText";
        }

        leaf SeverityLevel {
            tlv:id 3;
            tlv:repr uint8;
            type enumeration {
                enum emergency      { value  0; description ""; }
                enum alert          { value  1; description ""; }
                enum critical       { value  2; description ""; }
                enum error          { value  3; description ""; }
                enum warning        { value  4; description ""; }
                enum notice         { value  5; description ""; }
                enum information    { value  6; description ""; }
                enum debug          { value  7; description ""; }
            }
            description "TLV [100.4.3]: RpdInfo.DiagnosticStatus.SeverityLevel";
        }

    }  // g-DiagnosticStatus grouping

}
