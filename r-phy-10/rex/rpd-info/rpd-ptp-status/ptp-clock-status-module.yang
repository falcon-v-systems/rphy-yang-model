module ptp-clock-status-module {
    yang-version 1;
    /* This file is automatically generated with Falcon V System's script.
       Any change made to this file will be lost. */

    namespace "falconvsystems:r-phy-10:ptp-clock-status-module";
    prefix "p-ptp-clock-status";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-PtpClockStatus {
        tlv:id 2;
        description "TLV [100.24.2]: RpdInfo.RpdPtpStatus.PtpClockStatus";

        leaf ClockState {
            tlv:id 1;
            tlv:repr uint8;
            type enumeration {
                enum freerun        { value  1; description ""; }
                enum holdover       { value  2; description ""; }
                enum acquiring      { value  3; description ""; }
                enum freqLocked     { value  4; description ""; }
                enum phaseAligned   { value  5; description ""; }
            }
            description
                "TLV [100.24.2.1]: RpdInfo.RpdPtpStatus.PtpClockStatus.ClockState";
        }

        leaf LastStateChange {
            tlv:id 2;
            type uint64;
            description
                "TLV [100.24.2.2]: RpdInfo.RpdPtpStatus.PtpClockStatus.LastStateChange";
        }

        leaf PacketsSent {
            tlv:id 3;
            type uint64;
            description
                "TLV [100.24.2.3]: RpdInfo.RpdPtpStatus.PtpClockStatus.PacketsSent";
        }

        leaf PacketsReceived {
            tlv:id 4;
            type uint64;
            description
                "TLV [100.24.2.4]: RpdInfo.RpdPtpStatus.PtpClockStatus.PacketsReceived";
        }

        leaf CounterDiscontinuityTime {
            tlv:id 6;
            type binary;
            description
                "TLV [100.24.2.6]: RpdInfo.RpdPtpStatus.PtpClockStatus.CounterDiscontinuityTime";
        }

        leaf ExcessiveHoldover {
            tlv:id 7;
            type boolean;
            description
                "TLV [100.24.2.7]: RpdInfo.RpdPtpStatus.PtpClockStatus.ExcessiveHoldover";
        }

    }  // g-PtpClockStatus grouping

}
