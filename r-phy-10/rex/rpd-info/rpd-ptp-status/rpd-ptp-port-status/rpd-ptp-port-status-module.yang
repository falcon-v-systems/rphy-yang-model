module rpd-ptp-port-status-module {
    yang-version 1;
    /* This file is automatically generated with Falcon V System's script.
       Any change made to this file will be lost. */

    namespace "falconvsystems:r-phy-10:rpd-ptp-port-status-module";
    prefix "p-rpd-ptp-port-status";

    // --- imports ---------------------------------------

    import ptp-port-master-clock-status-module {
        prefix "p-ptp-port-master-clock-status";
        /*  File path: rex/rpd-info/rpd-ptp-status/rpd-ptp-port-status/ptp-port-master-clock-status-module.yang
            https://github.com/falcon-v-systems/rphy-yang-model/blob/master/r-phy-10/rex/rpd-info/rpd-ptp-status/rpd-ptp-port-status/ptp-port-master-clock-status-module.yang */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-RpdPtpPortStatus {
        tlv:id 4;
        description "TLV [100.24.4]: RpdInfo.RpdPtpStatus.RpdPtpPortStatus";

        leaf RpdEnetPortIndex {
            tlv:id 1;
            type uint8;
            description
                "TLV [100.24.4.1]: RpdInfo.RpdPtpStatus.RpdPtpPortStatus.RpdEnetPortIndex
                 non-defaults: [is_key: True]";
        }

        leaf RpdPtpPortIndex {
            tlv:id 2;
            type uint8;
            description
                "TLV [100.24.4.2]: RpdInfo.RpdPtpStatus.RpdPtpPortStatus.RpdPtpPortIndex
                 non-defaults: [is_key: True]";
        }

        leaf PacketsSent {
            tlv:id 3;
            type uint64;
            description
                "TLV [100.24.4.3]: RpdInfo.RpdPtpStatus.RpdPtpPortStatus.PacketsSent";
        }

        leaf PacketsReceived {
            tlv:id 4;
            type uint64;
            description
                "TLV [100.24.4.4]: RpdInfo.RpdPtpStatus.RpdPtpPortStatus.PacketsReceived";
        }

        leaf CounterDiscontinuityTime {
            tlv:id 5;
            type binary;
            description
                "TLV [100.24.4.5]: RpdInfo.RpdPtpStatus.RpdPtpPortStatus.CounterDiscontinuityTime";
        }

        list PtpPortMasterClockStatus {
            tlv:id 6;
            key "MasterPriority";
            description
                "TLV [100.24.4.6]: RpdInfo.RpdPtpStatus.RpdPtpPortStatus.PtpPortMasterClockStatus";
            uses "p-ptp-port-master-clock-status:g-PtpPortMasterClockStatus";
        }

    }  // g-RpdPtpPortStatus grouping

}
