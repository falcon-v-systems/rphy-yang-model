module ptp-current-dataset-module {
    yang-version 1;
    /* This file is automatically generated with Falcon V System's script.
       Any change made to this file will be lost. */

    namespace "falconvsystems:r-phy-10:ptp-current-dataset-module";
    prefix "p-ptp-current-dataset";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-PtpCurrentDataset {
        tlv:id 1;
        description "TLV [100.24.1]: RpdInfo.RpdPtpStatus.PtpCurrentDataset";

        leaf StepsRemoved {
            tlv:id 1;
            type uint32;
            description
                "TLV [100.24.1.1]: RpdInfo.RpdPtpStatus.PtpCurrentDataset.StepsRemoved";
        }

        leaf OffsetFromMaster {
            tlv:id 2;
            type int64;
            description
                "TLV [100.24.1.2]: RpdInfo.RpdPtpStatus.PtpCurrentDataset.OffsetFromMaster";
        }

        leaf MeanPathDelay {
            tlv:id 3;
            type uint32;
            description
                "TLV [100.24.1.3]: RpdInfo.RpdPtpStatus.PtpCurrentDataset.MeanPathDelay";
        }

    }  // g-PtpCurrentDataset grouping

}
