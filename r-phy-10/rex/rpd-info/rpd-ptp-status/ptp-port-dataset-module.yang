module ptp-port-dataset-module {
    yang-version 1;
    /* This file is automatically generated with Falcon V System's script.
       Any change made to this file will be lost. */

    namespace "falconvsystems:r-phy-10:ptp-port-dataset-module";
    prefix "p-ptp-port-dataset";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-PtpPortDataset {
        tlv:id 3;
        description "TLV [100.24.3]: RpdInfo.RpdPtpStatus.PtpPortDataset";

        leaf PortNumber {
            tlv:id 1;
            type uint16;
            description
                "TLV [100.24.3.1]: RpdInfo.RpdPtpStatus.PtpPortDataset.PortNumber
                 non-defaults: [is_key: True]";
        }

        leaf PortState {
            tlv:id 2;
            tlv:repr uint8;
            type enumeration {
                enum initializing   { value  1; description ""; }
                enum faulty         { value  2; description ""; }
                enum disabled       { value  3; description ""; }
                enum listening      { value  4; description ""; }
                enum preMaster      { value  5; description ""; }
                enum master         { value  6; description ""; }
                enum passive        { value  7; description ""; }
                enum uncalibrated   { value  8; description ""; }
                enum slave          { value  9; description ""; }
            }
            description
                "TLV [100.24.3.2]: RpdInfo.RpdPtpStatus.PtpPortDataset.PortState";
        }

        leaf MeanPathDelay {
            tlv:id 3;
            type int32;
            description
                "TLV [100.24.3.3]: RpdInfo.RpdPtpStatus.PtpPortDataset.MeanPathDelay";
        }

    }  // g-PtpPortDataset grouping

}
