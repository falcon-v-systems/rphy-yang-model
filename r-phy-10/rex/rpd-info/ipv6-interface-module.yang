module ipv6-interface-module {
    yang-version 1;
    /* This file is automatically generated with Falcon V System's script.
       Any change made to this file will be lost. */

    namespace "falconvsystems:r-phy-10:ipv6-interface-module";
    prefix "p-ipv6-interface";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-Ipv6Interface {
        tlv:id 13;
        description "TLV [100.13]: RpdInfo.Ipv6Interface";

        leaf EnetPortIndex {
            tlv:id 1;
            type uint8;
            description
                "TLV [100.13.1]: RpdInfo.Ipv6Interface.EnetPortIndex
                 non-defaults: [is_key: True]";
        }

        leaf EnableStatus {
            tlv:id 3;
            tlv:repr uint8;
            type enumeration {
                enum up     { value  1; description ""; }
                enum down   { value  2; description ""; }
            }
            description "TLV [100.13.3]: RpdInfo.Ipv6Interface.EnableStatus";
        }

        leaf RetransmitTime {
            tlv:id 4;
            type uint32;
            units "milliseconds";
            description "TLV [100.13.4]: RpdInfo.Ipv6Interface.RetransmitTime";
        }

        leaf InterfaceIdentifier {
            tlv:id 5;
            type binary;
            description "TLV [100.13.5]: RpdInfo.Ipv6Interface.InterfaceIdentifier";
        }

        leaf ReachableTime {
            tlv:id 6;
            type uint32;
            units "milliseconds";
            description "TLV [100.13.6]: RpdInfo.Ipv6Interface.ReachableTime";
        }

    }  // g-Ipv6Interface grouping

}
