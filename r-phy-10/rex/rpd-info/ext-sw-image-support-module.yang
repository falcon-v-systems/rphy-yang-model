module ext-sw-image-support-module {
    yang-version 1;
    /* This file is automatically generated with Falcon V System's script.
       Any change made to this file will be lost. */

    namespace "falconvsystems:r-phy-10:ext-sw-image-support-module";
    prefix "p-ext-sw-image-support";

    // --- imports ---------------------------------------

    import ietf-inet-types {
        prefix "inet";
        /*  External YANG module. */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-ExtSwImageSupport {
        tlv:id 25;
        description "TLV [100.25]: RpdInfo.ExtSwImageSupport";

        leaf SwImageIndex {
            tlv:id 1;
            type uint8;
            description
                "TLV [100.25.1]: RpdInfo.ExtSwImageSupport.SwImageIndex
                 non-defaults: [is_key: True]";
        }

        leaf SwImageLastUpdate {
            tlv:id 2;
            type binary;
            description "TLV [100.25.2]: RpdInfo.ExtSwImageSupport.SwImageLastUpdate";
        }

        leaf SwImageName {
            tlv:id 3;
            type string;
            description "TLV [100.25.3]: RpdInfo.ExtSwImageSupport.SwImageName";
        }

        leaf SwImageDescr {
            tlv:id 4;
            type string;
            description "TLV [100.25.4]: RpdInfo.ExtSwImageSupport.SwImageDescr";
        }

        leaf SwImageServerAddress {
            tlv:id 5;
            type inet:ip-address;
            description
                "TLV [100.25.5]: RpdInfo.ExtSwImageSupport.SwImageServerAddress";
        }

    }  // g-ExtSwImageSupport grouping

}
