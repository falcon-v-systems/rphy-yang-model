module host-resources-sw-run-module {
    yang-version 1;
    /* This file is automatically generated with Falcon V System's script.
       Any change made to this file will be lost. */

    namespace "falconvsystems:r-phy-10:host-resources-sw-run-module";
    prefix "p-host-resources-sw-run";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-HostResourcesSwRun {
        tlv:id 23;
        description "TLV [100.23]: RpdInfo.HostResourcesSwRun";

        leaf Index {
            tlv:id 1;
            type uint32;
            description
                "TLV [100.23.1]: RpdInfo.HostResourcesSwRun.Index
                 non-defaults: [is_key: True]";
        }

        leaf Type {
            tlv:id 2;
            tlv:repr uint8;
            type enumeration {
                enum unknown            { value  1; description ""; }
                enum operatingSystem    { value  2; description ""; }
                enum deviceDriver       { value  3; description ""; }
                enum application        { value  4; description ""; }
            }
            description "TLV [100.23.2]: RpdInfo.HostResourcesSwRun.Type";
        }

        leaf Status {
            tlv:id 3;
            tlv:repr uint8;
            type enumeration {
                enum running        { value  1; description ""; }
                enum runnable       { value  2; description ""; }
                enum notRunnable    { value  3; description ""; }
                enum invalid        { value  4; description ""; }
            }
            description "TLV [100.23.3]: RpdInfo.HostResourcesSwRun.Status";
        }

        leaf PerfCpu {
            tlv:id 4;
            type uint32;
            description "TLV [100.23.4]: RpdInfo.HostResourcesSwRun.PerfCpu";
        }

        leaf PerfMem {
            tlv:id 5;
            type uint32;
            description "TLV [100.23.5]: RpdInfo.HostResourcesSwRun.PerfMem";
        }

        leaf Name {
            tlv:id 6;
            type string;
            description "TLV [100.23.6]: RpdInfo.HostResourcesSwRun.Name";
        }

    }  // g-HostResourcesSwRun grouping

}
