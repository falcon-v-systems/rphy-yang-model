module entity-module {
    yang-version 1;
    /* This file is automatically generated with Falcon V System's script.
       Any change made to this file will be lost. */

    namespace "falconvsystems:r-phy-10:entity-module";
    prefix "p-entity";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-Entity {
        tlv:id 6;
        description "TLV [100.6]: RpdInfo.Entity";

        leaf EntityIndex {
            tlv:id 1;
            type uint32;
            description
                "TLV [100.6.1]: RpdInfo.Entity.EntityIndex
                 non-defaults: [is_key: True]";
        }

        leaf Descr {
            tlv:id 2;
            type string;
            description "TLV [100.6.2]: RpdInfo.Entity.Descr";
        }

        leaf VendorType {
            tlv:id 3;
            type string;
            description "TLV [100.6.3]: RpdInfo.Entity.VendorType";
        }

        leaf ContainedIn {
            tlv:id 4;
            type uint32;
            description "TLV [100.6.4]: RpdInfo.Entity.ContainedIn";
        }

        leaf Class {
            tlv:id 5;
            tlv:repr uint8;
            type enumeration {
                enum other          { value  1; description ""; }
                enum unknown        { value  2; description ""; }
                enum chassis        { value  3; description ""; }
                enum backplane      { value  4; description ""; }
                enum container      { value  5; description ""; }
                enum powerSupply    { value  6; description ""; }
                enum fan            { value  7; description ""; }
                enum sensor         { value  8; description ""; }
                enum module         { value  9; description ""; }
                enum port           { value 10; description ""; }
                enum stack          { value 11; description ""; }
                enum cpu            { value 12; description ""; }
            }
            description "TLV [100.6.5]: RpdInfo.Entity.Class";
        }

        leaf ParentRelPos {
            tlv:id 6;
            type uint32;
            description "TLV [100.6.6]: RpdInfo.Entity.ParentRelPos";
        }

        leaf Name {
            tlv:id 7;
            type string;
            description "TLV [100.6.7]: RpdInfo.Entity.Name";
        }

        leaf HardwareRev {
            tlv:id 8;
            type string;
            description "TLV [100.6.8]: RpdInfo.Entity.HardwareRev";
        }

        leaf FirmwareRev {
            tlv:id 9;
            type string;
            description "TLV [100.6.9]: RpdInfo.Entity.FirmwareRev";
        }

        leaf SoftwareRev {
            tlv:id 10;
            type string;
            description "TLV [100.6.10]: RpdInfo.Entity.SoftwareRev";
        }

        leaf SerialNum {
            tlv:id 11;
            type string;
            description "TLV [100.6.11]: RpdInfo.Entity.SerialNum";
        }

        leaf MfgName {
            tlv:id 12;
            type string;
            description "TLV [100.6.12]: RpdInfo.Entity.MfgName";
        }

        leaf ModelName {
            tlv:id 13;
            type string;
            description "TLV [100.6.13]: RpdInfo.Entity.ModelName";
        }

        leaf Alias {
            tlv:id 14;
            type string;
            description "TLV [100.6.14]: RpdInfo.Entity.Alias";
        }

        leaf AssetId {
            tlv:id 15;
            type string;
            description "TLV [100.6.15]: RpdInfo.Entity.AssetId";
        }

        leaf IsFRU {
            tlv:id 16;
            type boolean;
            description "TLV [100.6.16]: RpdInfo.Entity.IsFRU";
        }

        leaf MfgDate {
            tlv:id 17;
            type binary;
            description "TLV [100.6.17]: RpdInfo.Entity.MfgDate";
        }

        leaf Uris {
            tlv:id 18;
            type binary;
            description "TLV [100.6.18]: RpdInfo.Entity.Uris";
        }

        leaf Uuid {
            tlv:id 20;
            type binary;
            description "TLV [100.6.20]: RpdInfo.Entity.Uuid";
        }

    }  // g-Entity grouping

}
