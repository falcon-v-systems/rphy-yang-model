module rpd-aaa-server-auth-module {
    yang-version 1;
    /* This file is automatically generated with Falcon V System's script.
       Any change made to this file will be lost. */

    namespace "falconvsystems:r-phy-10:rpd-aaa-server-auth-module";
    prefix "p-rpd-aaa-server-auth";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-RpdAaaServerAuth {
        tlv:id 28;
        description "TLV [100.28]: RpdInfo.RpdAaaServerAuth";

        leaf Status {
            tlv:id 1;
            tlv:repr uint8;
            type enumeration {
                enum authenticated      { value  1; description ""; }
                enum authFailed         { value  2; description ""; }
                enum authNotPerformed   { value  3; description ""; }
            }
            description "TLV [100.28.1]: RpdInfo.RpdAaaServerAuth.Status";
        }

    }  // g-RpdAaaServerAuth grouping

}
