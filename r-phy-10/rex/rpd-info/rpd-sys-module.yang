module rpd-sys-module {
    yang-version 1;
    /* This file is automatically generated with Falcon V System's script.
       Any change made to this file will be lost. */

    namespace "falconvsystems:r-phy-10:rpd-sys-module";
    prefix "p-rpd-sys";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-RpdSys {
        tlv:id 1;
        description "TLV [100.1]: RpdInfo.RpdSys";

        leaf RpdSysUpTime {
            tlv:id 1;
            type uint32;
            description "TLV [100.1.1]: RpdInfo.RpdSys.RpdSysUpTime";
        }

        leaf NumCrashFilesAvail {
            tlv:id 2;
            type uint8;
            description "TLV [100.1.2]: RpdInfo.RpdSys.NumCrashFilesAvail";
        }

    }  // g-RpdSys grouping

}
