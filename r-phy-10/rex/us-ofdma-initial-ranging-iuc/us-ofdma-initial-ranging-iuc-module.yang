module us-ofdma-initial-ranging-iuc-module {
    yang-version 1;
    /* This file is automatically generated with Falcon V System's script.
       Any change made to this file will be lost. */

    namespace "falconvsystems:r-phy-10:us-ofdma-initial-ranging-iuc-module";
    prefix "p-us-ofdma-initial-ranging-iuc";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UsOfdmaInitialRangingIuc {
        tlv:id 67;
        description "TLV [67]: UsOfdmaInitialRangingIuc";

        leaf NumSubcarriers {
            tlv:id 1;
            type uint16;
            description
                "TLV [67.1]: UsOfdmaInitialRangingIuc.NumSubcarriers
                 non-defaults: [is_rcp_readonly: True]";
        }

        leaf Guardband {
            tlv:id 2;
            type uint16;
            description
                "TLV [67.2]: UsOfdmaInitialRangingIuc.Guardband
                 non-defaults: [is_rcp_readonly: True]";
        }

    }  // g-UsOfdmaInitialRangingIuc grouping

}
