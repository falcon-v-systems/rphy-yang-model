module core-gcp-connection-response-module {
    yang-version 1;
    /* This file is automatically generated with Falcon V System's script.
       Any change made to this file will be lost. */

    namespace "falconvsystems:r-phy-10:core-gcp-connection-response-module";
    prefix "p-core-gcp-connection-response";

    // --- imports ---------------------------------------

    import ietf-yang-types {
        prefix "yang";
        /*  External YANG module. */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-CoreGcpConnectionResponse {
        tlv:id 106;
        description "TLV [106]: CoreGcpConnectionResponse";

        leaf CoreId {
            tlv:id 1;
            type yang:mac-address;
            description "TLV [106.1]: CoreGcpConnectionResponse.CoreId";
        }

        leaf Response {
            tlv:id 2;
            tlv:repr uint8;
            type enumeration {
                enum noAction   { value  0; description ""; }
                enum Accept     { value  1; description ""; }
                enum Reject     { value  2; description ""; }
            }
            description "TLV [106.2]: CoreGcpConnectionResponse.Response";
        }

    }  // g-CoreGcpConnectionResponse grouping

}
