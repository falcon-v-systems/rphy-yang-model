module ds-chan-group-module {
    yang-version 1;
    /* This file is automatically generated with Falcon V System's script.
       Any change made to this file will be lost. */

    namespace "falconvsystems:r-phy-10:ds-chan-group-module";
    prefix "p-ds-chan-group";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-DsChanGroup {
        tlv:id 5;
        description "TLV [88.2.5]: MultiCore.ResourceSet.DsChanGroup";

        leaf DsChanGroupIndex {
            tlv:id 1;
            type uint32;
            description
                "TLV [88.2.5.1]: MultiCore.ResourceSet.DsChanGroup.DsChanGroupIndex";
        }

        leaf DsChanType {
            tlv:id 2;
            tlv:repr uint8;
            type enumeration {
                enum DsScQam    { value  1; description ""; }
                enum DsOfdm     { value  2; description ""; }
                enum Ndf        { value  3; description ""; }
                enum DsScte55d1 { value  4; description ""; }
            }
            description "TLV [88.2.5.2]: MultiCore.ResourceSet.DsChanGroup.DsChanType";
        }

        leaf DsChanIndexStart {
            tlv:id 3;
            type uint32;
            description
                "TLV [88.2.5.3]: MultiCore.ResourceSet.DsChanGroup.DsChanIndexStart";
        }

        leaf DsChanIndexEnd {
            tlv:id 4;
            type uint32;
            description
                "TLV [88.2.5.4]: MultiCore.ResourceSet.DsChanGroup.DsChanIndexEnd";
        }

    }  // g-DsChanGroup grouping

}
