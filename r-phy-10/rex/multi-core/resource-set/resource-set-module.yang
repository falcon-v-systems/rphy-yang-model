module resource-set-module {
    yang-version 1;
    /* This file is automatically generated with Falcon V System's script.
       Any change made to this file will be lost. */

    namespace "falconvsystems:r-phy-10:resource-set-module";
    prefix "p-resource-set";

    // --- imports ---------------------------------------

    import ds-chan-group-module {
        prefix "p-ds-chan-group";
        /*  File path: rex/multi-core/resource-set/ds-chan-group-module.yang
            https://github.com/falcon-v-systems/rphy-yang-model/blob/master/r-phy-10/rex/multi-core/resource-set/ds-chan-group-module.yang */
    }

    import ietf-yang-types {
        prefix "yang";
        /*  External YANG module. */
    }

    import tlv-extension {
        prefix "tlv";
        /*  Falcon's Yang extension for TLV attributes. */
    }

    import us-chan-group-module {
        prefix "p-us-chan-group";
        /*  File path: rex/multi-core/resource-set/us-chan-group-module.yang
            https://github.com/falcon-v-systems/rphy-yang-model/blob/master/r-phy-10/rex/multi-core/resource-set/us-chan-group-module.yang */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-ResourceSet {
        tlv:id 2;
        description "TLV [88.2]: MultiCore.ResourceSet";

        leaf ResourceSetIndex {
            tlv:id 1;
            type uint8;
            description
                "TLV [88.2.1]: MultiCore.ResourceSet.ResourceSetIndex
                 non-defaults: [is_key: True]";
        }

        leaf CcapCoreOwner {
            tlv:id 2;
            type yang:mac-address;
            description "TLV [88.2.2]: MultiCore.ResourceSet.CcapCoreOwner";
        }

        leaf DsRfPortStart {
            tlv:id 3;
            type uint32;
            description "TLV [88.2.3]: MultiCore.ResourceSet.DsRfPortStart";
        }

        leaf DsRfPortEnd {
            tlv:id 4;
            type uint32;
            description "TLV [88.2.4]: MultiCore.ResourceSet.DsRfPortEnd";
        }

        container DsChanGroup {
            tlv:id 5;
            description "TLV [88.2.5]: MultiCore.ResourceSet.DsChanGroup";
            uses "p-ds-chan-group:g-DsChanGroup";
        }

        leaf UsRfPortStart {
            tlv:id 6;
            type uint32;
            description "TLV [88.2.6]: MultiCore.ResourceSet.UsRfPortStart";
        }

        leaf UsRfPortEnd {
            tlv:id 7;
            type uint32;
            description "TLV [88.2.7]: MultiCore.ResourceSet.UsRfPortEnd";
        }

        container UsChanGroup {
            tlv:id 8;
            description "TLV [88.2.8]: MultiCore.ResourceSet.UsChanGroup";
            uses "p-us-chan-group:g-UsChanGroup";
        }

    }  // g-ResourceSet grouping

}
