module us-chan-group-module {
    yang-version 1;
    /* This file is automatically generated with Falcon V System's script.
       Any change made to this file will be lost. */

    namespace "falconvsystems:r-phy-10:us-chan-group-module";
    prefix "p-us-chan-group";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UsChanGroup {
        tlv:id 8;
        description "TLV [88.2.8]: MultiCore.ResourceSet.UsChanGroup";

        leaf UsChanGroupIndex {
            tlv:id 1;
            type int32;
            description
                "TLV [88.2.8.1]: MultiCore.ResourceSet.UsChanGroup.UsChanGroupIndex";
        }

        leaf UsChanType {
            tlv:id 2;
            tlv:repr uint8;
            type enumeration {
                enum UsAtdma    { value  5; description ""; }
                enum UsOfdma    { value  6; description ""; }
                enum Ndr        { value  8; description ""; }
                enum UsScte55d1 { value  9; description ""; }
            }
            description "TLV [88.2.8.2]: MultiCore.ResourceSet.UsChanGroup.UsChanType";
        }

        leaf UsChanIndexStart {
            tlv:id 3;
            type uint32;
            description
                "TLV [88.2.8.3]: MultiCore.ResourceSet.UsChanGroup.UsChanIndexStart";
        }

        leaf UsChanIndexEnd {
            tlv:id 4;
            type uint32;
            description
                "TLV [88.2.8.4]: MultiCore.ResourceSet.UsChanGroup.UsChanIndexEnd";
        }

    }  // g-UsChanGroup grouping

}
