module configured-core-table-module {
    yang-version 1;
    /* This file is automatically generated with Falcon V System's script.
       Any change made to this file will be lost. */

    namespace "falconvsystems:r-phy-10:configured-core-table-module";
    prefix "p-configured-core-table";

    // --- imports ---------------------------------------

    import ietf-inet-types {
        prefix "inet";
        /*  External YANG module. */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-ConfiguredCoreTable {
        tlv:id 1;
        description
            "TLV [88.1]: MultiCore.ConfiguredCoreTable
             non-defaults: [is_rcp_readonly: True, is_readonly: True]";

        leaf Index {
            tlv:id 1;
            type uint8;
            description "TLV [88.1.1]: MultiCore.ConfiguredCoreTable.Index";
        }

        leaf ConfiguredCoreIp {
            tlv:id 2;
            type inet:ip-address;
            description
                "TLV [88.1.2]: MultiCore.ConfiguredCoreTable.ConfiguredCoreIp
                 non-defaults: [is_rcp_readonly: True, is_readonly: True]";
        }

    }  // g-ConfiguredCoreTable grouping

}
