module ds-ofdm-profile-perf-module {
    yang-version 1;
    /* This file is automatically generated with Falcon V System's script.
       Any change made to this file will be lost. */

    namespace "falconvsystems:r-phy-10:ds-ofdm-profile-perf-module";
    prefix "p-ds-ofdm-profile-perf";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-DsOfdmProfilePerf {
        tlv:id 3;
        description
            "TLV [73.3]: DsOfdmChannelPerf.DsOfdmProfilePerf
             non-defaults: [is_rcp_readonly: True, is_readonly: True]";

        leaf ProfileIndex {
            tlv:id 1;
            type uint8;
            description
                "TLV [73.3.1]: DsOfdmChannelPerf.DsOfdmProfilePerf.ProfileIndex";
        }

        leaf outCodewords {
            tlv:id 2;
            type uint64;
            description
                "TLV [73.3.2]: DsOfdmChannelPerf.DsOfdmProfilePerf.outCodewords
                 non-defaults: [is_rcp_readonly: True, is_readonly: True]";
        }

    }  // g-DsOfdmProfilePerf grouping

}
