module ds-ofdm-plc-perf-module {
    yang-version 1;
    /* This file is automatically generated with Falcon V System's script.
       Any change made to this file will be lost. */

    namespace "falconvsystems:r-phy-10:ds-ofdm-plc-perf-module";
    prefix "p-ds-ofdm-plc-perf";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-DsOfdmPlcPerf {
        tlv:id 6;
        description
            "TLV [73.6]: DsOfdmChannelPerf.DsOfdmPlcPerf
             non-defaults: [is_rcp_readonly: True, is_readonly: True]";

        leaf outDiscards {
            tlv:id 1;
            type uint64;
            units "packets";
            description
                "TLV [73.6.1]: DsOfdmChannelPerf.DsOfdmPlcPerf.outDiscards
                 non-defaults: [is_rcp_readonly: True, is_readonly: True]";
        }

        leaf outErrors {
            tlv:id 2;
            type uint64;
            units "packets";
            description
                "TLV [73.6.2]: DsOfdmChannelPerf.DsOfdmPlcPerf.outErrors
                 non-defaults: [is_rcp_readonly: True, is_readonly: True]";
        }

        leaf outPackets {
            tlv:id 3;
            type uint64;
            units "packets";
            description
                "TLV [73.6.3]: DsOfdmChannelPerf.DsOfdmPlcPerf.outPackets
                 non-defaults: [is_rcp_readonly: True, is_readonly: True]";
        }

        leaf discontinuityTime {
            tlv:id 4;
            type binary;
            description
                "TLV [73.6.4]: DsOfdmChannelPerf.DsOfdmPlcPerf.discontinuityTime
                 non-defaults: [is_rcp_readonly: True, is_readonly: True]";
        }

    }  // g-DsOfdmPlcPerf grouping

}
