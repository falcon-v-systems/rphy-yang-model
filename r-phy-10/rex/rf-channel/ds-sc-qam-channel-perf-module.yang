module ds-sc-qam-channel-perf-module {
    yang-version 1;
    /* This file is automatically generated with Falcon V System's script.
       Any change made to this file will be lost. */

    namespace "falconvsystems:r-phy-10:ds-sc-qam-channel-perf-module";
    prefix "p-ds-sc-qam-channel-perf";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-DsScQamChannelPerf {
        tlv:id 72;
        description
            "TLV [72]: DsScQamChannelPerf
             non-defaults: [is_rcp_readonly: True, is_readonly: True]";

        leaf Index {
            // no tlv:id given
            type uint16;
            description
                "TLV [72.X]: DsScQamChannelPerf.Index
                 non-defaults: [is_key: True]";
        }

        leaf outDiscards {
            tlv:id 1;
            type uint64;
            units "packets";
            description
                "TLV [72.1]: DsScQamChannelPerf.outDiscards
                 non-defaults: [is_rcp_readonly: True, is_readonly: True]";
        }

        leaf outErrors {
            tlv:id 2;
            type uint64;
            units "packets";
            description
                "TLV [72.2]: DsScQamChannelPerf.outErrors
                 non-defaults: [is_rcp_readonly: True, is_readonly: True]";
        }

        leaf outPackets {
            tlv:id 3;
            type uint64;
            units "packets";
            description
                "TLV [72.3]: DsScQamChannelPerf.outPackets
                 non-defaults: [is_rcp_readonly: True, is_readonly: True]";
        }

        leaf discontinuityTime {
            tlv:id 4;
            type binary;
            description
                "TLV [72.4]: DsScQamChannelPerf.discontinuityTime
                 non-defaults: [is_rcp_readonly: True, is_readonly: True]";
        }

        leaf operStatusDsScQam {
            tlv:id 5;
            tlv:repr uint8;
            type enumeration {
                enum up     { value  1; description ""; }
                enum down   { value  2; description ""; }
            }
            description
                "TLV [72.5]: DsScQamChannelPerf.operStatusDsScQam
                 non-defaults: [is_rcp_readonly: True, is_readonly: True]";
        }

    }  // g-DsScQamChannelPerf grouping

}
