module us-ofdma-channel-config-module {
    yang-version 1;
    /* This file is automatically generated with Falcon V System's script.
       Any change made to this file will be lost. */

    namespace "falconvsystems:r-phy-10:us-ofdma-channel-config-module";
    prefix "p-us-ofdma-channel-config";

    // --- imports ---------------------------------------

    import bw-req-aggr-control-ofdma-module {
        prefix "p-bw-req-aggr-control-ofdma";
        /*  File path: rex/rf-channel/us-ofdma-channel-config/bw-req-aggr-control-ofdma-module.yang
            https://github.com/falcon-v-systems/rphy-yang-model/blob/master/r-phy-10/rex/rf-channel/us-ofdma-channel-config/bw-req-aggr-control-ofdma-module.yang */
    }

    import ietf-yang-types {
        prefix "yang";
        /*  External YANG module. */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UsOfdmaChannelConfig {
        tlv:id 66;
        description "TLV [66]: UsOfdmaChannelConfig";

        leaf Index {
            // no tlv:id given
            type uint16;
            description
                "TLV [66.X]: UsOfdmaChannelConfig.Index
                 non-defaults: [is_key: True]";
        }

        leaf AdminState {
            tlv:id 1;
            tlv:repr uint8;
            type enumeration {
                enum other      { value  1; description ""; }
                enum up         { value  2; description ""; }
                enum down       { value  3; description ""; }
                enum testing    { value  4; description ""; }
            }
            description "TLV [66.1]: UsOfdmaChannelConfig.AdminState";
        }

        leaf CcapCoreOwner {
            tlv:id 2;
            type yang:mac-address;
            description "TLV [66.2]: UsOfdmaChannelConfig.CcapCoreOwner";
        }

        leaf SubcarrierZeroFreq {
            tlv:id 3;
            type uint32;
            units "Hz";
            description
                "TLV [66.3]: UsOfdmaChannelConfig.SubcarrierZeroFreq
                 non-defaults: [is_rcp_readonly: True]";
        }

        leaf FirstActiveSubcarrierNum {
            tlv:id 4;
            type uint16;
            description
                "TLV [66.4]: UsOfdmaChannelConfig.FirstActiveSubcarrierNum
                 non-defaults: [is_rcp_readonly: True]";
        }

        leaf LastActiveSubcarrierNum {
            tlv:id 5;
            type uint16;
            description
                "TLV [66.5]: UsOfdmaChannelConfig.LastActiveSubcarrierNum
                 non-defaults: [is_rcp_readonly: True]";
        }

        leaf RollOffPeriod {
            tlv:id 6;
            tlv:repr uint16;
            type enumeration {
                enum 0      { value  1; description ""; }
                enum 32     { value  2; description ""; }
                enum 64     { value  3; description ""; }
                enum 96     { value  4; description ""; }
                enum 128    { value  5; description ""; }
                enum 160    { value  6; description ""; }
                enum 192    { value  7; description ""; }
                enum 224    { value  8; description ""; }
            }
            description
                "TLV [66.6]: UsOfdmaChannelConfig.RollOffPeriod
                 non-defaults: [is_rcp_readonly: True]";
        }

        leaf CyclicPrefix {
            tlv:id 7;
            tlv:repr uint16;
            type enumeration {
                enum 96     { value  1; description ""; }
                enum 128    { value  2; description ""; }
                enum 160    { value  3; description ""; }
                enum 192    { value  4; description ""; }
                enum 224    { value  5; description ""; }
                enum 256    { value  6; description ""; }
                enum 288    { value  7; description ""; }
                enum 320    { value  8; description ""; }
                enum 384    { value  9; description ""; }
                enum 512    { value 10; description ""; }
                enum 640    { value 11; description ""; }
            }
            description
                "TLV [66.7]: UsOfdmaChannelConfig.CyclicPrefix
                 non-defaults: [is_rcp_readonly: True]";
        }

        leaf SubcarrierSpacing {
            tlv:id 8;
            tlv:repr uint8;
            type enumeration {
                enum 25KHz  { value  1; description ""; }
                enum 50KHz  { value  2; description ""; }
            }
            description
                "TLV [66.8]: UsOfdmaChannelConfig.SubcarrierSpacing
                 non-defaults: [is_rcp_readonly: True]";
        }

        leaf NumSymbolsPerFrame {
            tlv:id 9;
            type uint8;
            description
                "TLV [66.9]: UsOfdmaChannelConfig.NumSymbolsPerFrame
                 non-defaults: [is_rcp_readonly: True]";
        }

        leaf NumActiveSubcarriers {
            tlv:id 10;
            type uint16;
            description
                "TLV [66.10]: UsOfdmaChannelConfig.NumActiveSubcarriers
                 non-defaults: [is_rcp_readonly: True]";
        }

        leaf StartingMinislot {
            tlv:id 11;
            type uint32;
            description "TLV [66.11]: UsOfdmaChannelConfig.StartingMinislot";
        }

        leaf PreambleString {
            tlv:id 12;
            type binary;
            description
                "TLV [66.12]: UsOfdmaChannelConfig.PreambleString
                 non-defaults: [is_rcp_readonly: True]";
        }

        leaf TargetRxPowerAdjust {
            tlv:id 13;
            type uint16;
            units "TenthdBmV";
            description "TLV [66.13]: UsOfdmaChannelConfig.TargetRxPowerAdjust";
        }

        leaf EnableFlowTags {
            tlv:id 14;
            type boolean;
            description "TLV [66.14]: UsOfdmaChannelConfig.EnableFlowTags";
        }

        leaf ScramblerSeed {
            tlv:id 15;
            type uint32;
            description
                "TLV [66.15]: UsOfdmaChannelConfig.ScramblerSeed
                 non-defaults: [is_rcp_readonly: True]";
        }

        leaf ConfigMultiSectionTimingMer {
            tlv:id 16;
            type binary;
            description
                "TLV [66.16]: UsOfdmaChannelConfig.ConfigMultiSectionTimingMer";
        }

        container BwReqAggrControlOfdma {
            tlv:id 17;
            description "TLV [66.17]: UsOfdmaChannelConfig.BwReqAggrControlOfdma";
            uses "p-bw-req-aggr-control-ofdma:g-BwReqAggrControlOfdma";
        }

        leaf UsChanId {
            tlv:id 18;
            type uint8;
            description
                "TLV [66.18]: UsOfdmaChannelConfig.UsChanId
                 non-defaults: [is_rcp_readonly: True, is_readonly: True]";
        }

        leaf ConfigChangeCount {
            tlv:id 19;
            type uint8;
            description
                "TLV [66.19]: UsOfdmaChannelConfig.ConfigChangeCount
                 non-defaults: [is_rcp_readonly: True, is_readonly: True]";
        }

        leaf DsChanId {
            tlv:id 20;
            type uint8;
            description
                "TLV [66.20]: UsOfdmaChannelConfig.DsChanId
                 non-defaults: [is_rcp_readonly: True, is_readonly: True]";
        }

        leaf BroadcastImRegionDuration {
            tlv:id 21;
            type uint8;
            description "TLV [66.21]: UsOfdmaChannelConfig.BroadcastImRegionDuration";
        }

        leaf UnicastImRegionDuration {
            tlv:id 22;
            type uint8;
            description "TLV [66.22]: UsOfdmaChannelConfig.UnicastImRegionDuration";
        }

    }  // g-UsOfdmaChannelConfig grouping

}
