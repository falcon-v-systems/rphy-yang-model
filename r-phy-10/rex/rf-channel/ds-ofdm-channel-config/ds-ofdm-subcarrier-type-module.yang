module ds-ofdm-subcarrier-type-module {
    yang-version 1;
    /* This file is automatically generated with Falcon V System's script.
       Any change made to this file will be lost. */

    namespace "falconvsystems:r-phy-10:ds-ofdm-subcarrier-type-module";
    prefix "p-ds-ofdm-subcarrier-type";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-DsOfdmSubcarrierType {
        tlv:id 13;
        description "TLV [63.13]: DsOfdmChannelConfig.DsOfdmSubcarrierType";

        leaf StartSubcarrierId {
            tlv:id 1;
            type uint16;
            description
                "TLV [63.13.1]: DsOfdmChannelConfig.DsOfdmSubcarrierType.StartSubcarrierId
                 non-defaults: [is_key: True]";
        }

        leaf EndSubcarrierId {
            tlv:id 2;
            type uint16;
            description
                "TLV [63.13.2]: DsOfdmChannelConfig.DsOfdmSubcarrierType.EndSubcarrierId
                 non-defaults: [is_rcp_readonly: True]";
        }

        leaf SubcarrierUsage {
            tlv:id 3;
            tlv:repr uint8;
            type enumeration {
                enum Other              { value  1; description ""; }
                enum Data               { value  2; description ""; }
                enum Plc                { value  3; description ""; }
                enum ContinuousPilot    { value  4; description ""; }
                enum Excluded           { value  5; description ""; }
                enum Unused             { value  6; description ""; }
            }
            description
                "TLV [63.13.3]: DsOfdmChannelConfig.DsOfdmSubcarrierType.SubcarrierUsage
                 non-defaults: [is_rcp_readonly: True]";
        }

    }  // g-DsOfdmSubcarrierType grouping

}
