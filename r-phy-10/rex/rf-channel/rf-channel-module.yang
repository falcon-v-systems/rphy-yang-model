module rf-channel-module {
    yang-version 1;
    /* This file is automatically generated with Falcon V System's script.
       Any change made to this file will be lost. */

    namespace "falconvsystems:r-phy-10:rf-channel-module";
    prefix "p-rf-channel";

    // --- imports ---------------------------------------

    import ds-ofdm-channel-config-module {
        prefix "p-ds-ofdm-channel-config";
        /*  File path: rex/rf-channel/ds-ofdm-channel-config/ds-ofdm-channel-config-module.yang
            https://github.com/falcon-v-systems/rphy-yang-model/blob/master/r-phy-10/rex/rf-channel/ds-ofdm-channel-config/ds-ofdm-channel-config-module.yang */
    }

    import ds-ofdm-channel-perf-module {
        prefix "p-ds-ofdm-channel-perf";
        /*  File path: rex/rf-channel/ds-ofdm-channel-perf/ds-ofdm-channel-perf-module.yang
            https://github.com/falcon-v-systems/rphy-yang-model/blob/master/r-phy-10/rex/rf-channel/ds-ofdm-channel-perf/ds-ofdm-channel-perf-module.yang */
    }

    import ds-oob551-perf-module {
        prefix "p-ds-oob551-perf";
        /*  File path: rex/rf-channel/ds-oob551-perf-module.yang
            https://github.com/falcon-v-systems/rphy-yang-model/blob/master/r-phy-10/rex/rf-channel/ds-oob551-perf-module.yang */
    }

    import ds-oob552-perf-module {
        prefix "p-ds-oob552-perf";
        /*  File path: rex/rf-channel/ds-oob552-perf-module.yang
            https://github.com/falcon-v-systems/rphy-yang-model/blob/master/r-phy-10/rex/rf-channel/ds-oob552-perf-module.yang */
    }

    import ds-sc-qam-channel-config-module {
        prefix "p-ds-sc-qam-channel-config";
        /*  File path: rex/rf-channel/ds-sc-qam-channel-config-module.yang
            https://github.com/falcon-v-systems/rphy-yang-model/blob/master/r-phy-10/rex/rf-channel/ds-sc-qam-channel-config-module.yang */
    }

    import ds-sc-qam-channel-perf-module {
        prefix "p-ds-sc-qam-channel-perf";
        /*  File path: rex/rf-channel/ds-sc-qam-channel-perf-module.yang
            https://github.com/falcon-v-systems/rphy-yang-model/blob/master/r-phy-10/rex/rf-channel/ds-sc-qam-channel-perf-module.yang */
    }

    import ndf-perf-module {
        prefix "p-ndf-perf";
        /*  File path: rex/rf-channel/ndf-perf-module.yang
            https://github.com/falcon-v-systems/rphy-yang-model/blob/master/r-phy-10/rex/rf-channel/ndf-perf-module.yang */
    }

    import ndr-perf-module {
        prefix "p-ndr-perf";
        /*  File path: rex/rf-channel/ndr-perf-module.yang
            https://github.com/falcon-v-systems/rphy-yang-model/blob/master/r-phy-10/rex/rf-channel/ndr-perf-module.yang */
    }

    import rf-channel-selector-module {
        prefix "p-rf-channel-selector";
        /*  File path: rex/rf-channel/rf-channel-selector-module.yang
            https://github.com/falcon-v-systems/rphy-yang-model/blob/master/r-phy-10/rex/rf-channel/rf-channel-selector-module.yang */
    }

    import tlv-extension {
        prefix "tlv";
        /*  Falcon's Yang extension for TLV attributes. */
    }

    import us-ofdma-channel-config-module {
        prefix "p-us-ofdma-channel-config";
        /*  File path: rex/rf-channel/us-ofdma-channel-config/us-ofdma-channel-config-module.yang
            https://github.com/falcon-v-systems/rphy-yang-model/blob/master/r-phy-10/rex/rf-channel/us-ofdma-channel-config/us-ofdma-channel-config-module.yang */
    }

    import us-ofdma-channel-perf-module {
        prefix "p-us-ofdma-channel-perf";
        /*  File path: rex/rf-channel/us-ofdma-channel-perf/us-ofdma-channel-perf-module.yang
            https://github.com/falcon-v-systems/rphy-yang-model/blob/master/r-phy-10/rex/rf-channel/us-ofdma-channel-perf/us-ofdma-channel-perf-module.yang */
    }

    import us-oob551-perf-module {
        prefix "p-us-oob551-perf";
        /*  File path: rex/rf-channel/us-oob551-perf-module.yang
            https://github.com/falcon-v-systems/rphy-yang-model/blob/master/r-phy-10/rex/rf-channel/us-oob551-perf-module.yang */
    }

    import us-oob552-perf-module {
        prefix "p-us-oob552-perf";
        /*  File path: rex/rf-channel/us-oob552-perf-module.yang
            https://github.com/falcon-v-systems/rphy-yang-model/blob/master/r-phy-10/rex/rf-channel/us-oob552-perf-module.yang */
    }

    import us-sc-qam-channel-config-module {
        prefix "p-us-sc-qam-channel-config";
        /*  File path: rex/rf-channel/us-sc-qam-channel-config/us-sc-qam-channel-config-module.yang
            https://github.com/falcon-v-systems/rphy-yang-model/blob/master/r-phy-10/rex/rf-channel/us-sc-qam-channel-config/us-sc-qam-channel-config-module.yang */
    }

    import us-sc-qam-channel-perf-module {
        prefix "p-us-sc-qam-channel-perf";
        /*  File path: rex/rf-channel/us-sc-qam-channel-perf/us-sc-qam-channel-perf-module.yang
            https://github.com/falcon-v-systems/rphy-yang-model/blob/master/r-phy-10/rex/rf-channel/us-sc-qam-channel-perf/us-sc-qam-channel-perf-module.yang */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-RfChannel {
        tlv:id 16;
        description "TLV [16]: RfChannel";

        container RfChannelSelector {
            tlv:id 12;
            description "TLV [12]: RfChannelSelector";
            uses "p-rf-channel-selector:g-RfChannelSelector";
        }

        leaf DocsisMsg {
            tlv:id 22;
            type binary;
            description "TLV [22]: DocsisMsg";
        }

        choice channel-topic {
            case DsScQamChannelConfig {
                list DsScQamChannelConfig {
                    tlv:id 62;
                    key "Index";
                    description "TLV [62]: DsScQamChannelConfig";
                    uses "p-ds-sc-qam-channel-config:g-DsScQamChannelConfig";
                }
            }

            case DsOfdmChannelConfig {
                list DsOfdmChannelConfig {
                    tlv:id 63;
                    key "Index";
                    description "TLV [63]: DsOfdmChannelConfig";
                    uses "p-ds-ofdm-channel-config:g-DsOfdmChannelConfig";
                }
            }

            case UsScQamChannelConfig {
                list UsScQamChannelConfig {
                    tlv:id 65;
                    key "Index";
                    description "TLV [65]: UsScQamChannelConfig";
                    uses "p-us-sc-qam-channel-config:g-UsScQamChannelConfig";
                }
            }

            case UsOfdmaChannelConfig {
                list UsOfdmaChannelConfig {
                    tlv:id 66;
                    key "Index";
                    description "TLV [66]: UsOfdmaChannelConfig";
                    uses "p-us-ofdma-channel-config:g-UsOfdmaChannelConfig";
                }
            }

            case DsScQamChannelPerf {
                list DsScQamChannelPerf {
                    tlv:id 72;
                    key "Index";
                    description
                        "TLV [72]: DsScQamChannelPerf
                         non-defaults: [is_rcp_readonly: True, is_readonly: True]";
                    uses "p-ds-sc-qam-channel-perf:g-DsScQamChannelPerf";
                }
            }

            case DsOfdmChannelPerf {
                list DsOfdmChannelPerf {
                    tlv:id 73;
                    key "Index";
                    description
                        "TLV [73]: DsOfdmChannelPerf
                         non-defaults: [is_rcp_readonly: True, is_readonly: True]";
                    uses "p-ds-ofdm-channel-perf:g-DsOfdmChannelPerf";
                }
            }

            case DsOob551Perf {
                container DsOob551Perf {
                    tlv:id 74;
                    description
                        "TLV [74]: DsOob551Perf
                         non-defaults: [is_rcp_readonly: True, is_readonly: True]";
                    uses "p-ds-oob551-perf:g-DsOob551Perf";
                }
            }

            case DsOob552Perf {
                container DsOob552Perf {
                    tlv:id 75;
                    description
                        "TLV [75]: DsOob552Perf
                         non-defaults: [is_rcp_readonly: True, is_readonly: True]";
                    uses "p-ds-oob552-perf:g-DsOob552Perf";
                }
            }

            case NdfPerf {
                list NdfPerf {
                    tlv:id 76;
                    key "Index";
                    description
                        "TLV [76]: NdfPerf
                         non-defaults: [is_rcp_readonly: True, is_readonly: True]";
                    uses "p-ndf-perf:g-NdfPerf";
                }
            }

            case UsScQamChannelPerf {
                list UsScQamChannelPerf {
                    tlv:id 78;
                    key "Index";
                    description
                        "TLV [78]: UsScQamChannelPerf
                         non-defaults: [is_rcp_readonly: True, is_readonly: True]";
                    uses "p-us-sc-qam-channel-perf:g-UsScQamChannelPerf";
                }
            }

            case UsOfdmaChannelPerf {
                list UsOfdmaChannelPerf {
                    tlv:id 79;
                    key "Index";
                    description "TLV [79]: UsOfdmaChannelPerf";
                    uses "p-us-ofdma-channel-perf:g-UsOfdmaChannelPerf";
                }
            }

            case UsOob551Perf {
                container UsOob551Perf {
                    tlv:id 80;
                    description
                        "TLV [80]: UsOob551Perf
                         non-defaults: [is_rcp_readonly: True, is_readonly: True]";
                    uses "p-us-oob551-perf:g-UsOob551Perf";
                }
            }

            case UsOob552Perf {
                container UsOob552Perf {
                    tlv:id 81;
                    description
                        "TLV [81]: UsOob552Perf
                         non-defaults: [is_rcp_readonly: True, is_readonly: True]";
                    uses "p-us-oob552-perf:g-UsOob552Perf";
                }
            }

            case NdrPerf {
                list NdrPerf {
                    tlv:id 82;
                    key "Index";
                    description
                        "TLV [82]: NdrPerf
                         non-defaults: [is_rcp_readonly: True, is_readonly: True]";
                    uses "p-ndr-perf:g-NdrPerf";
                }
            }

            description 
                "The choice statement defines a set of alternatives,
                 only one of which may exist at any one time.";
        }
    }  // g-RfChannel grouping

}
