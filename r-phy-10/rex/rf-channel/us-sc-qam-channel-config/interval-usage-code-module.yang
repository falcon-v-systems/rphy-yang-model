module interval-usage-code-module {
    yang-version 1;
    /* This file is automatically generated with Falcon V System's script.
       Any change made to this file will be lost. */

    namespace "falconvsystems:r-phy-10:interval-usage-code-module";
    prefix "p-interval-usage-code";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-IntervalUsageCode {
        tlv:id 10;
        description "TLV [65.10]: UsScQamChannelConfig.IntervalUsageCode";

        leaf Code {
            tlv:id 1;
            type uint8;
            description
                "TLV [65.10.1]: UsScQamChannelConfig.IntervalUsageCode.Code
                 non-defaults: [is_key: True]";
        }

        leaf DifferentialEncoding {
            tlv:id 2;
            type boolean;
            description
                "TLV [65.10.2]: UsScQamChannelConfig.IntervalUsageCode.DifferentialEncoding
                 non-defaults: [is_rcp_readonly: True]";
        }

        leaf FecErrorCorrectionT {
            tlv:id 3;
            type uint8;
            description
                "TLV [65.10.3]: UsScQamChannelConfig.IntervalUsageCode.FecErrorCorrectionT
                 non-defaults: [is_rcp_readonly: True]";
        }

        leaf FecCodewordLength {
            tlv:id 4;
            type uint8;
            units "bytes";
            description
                "TLV [65.10.4]: UsScQamChannelConfig.IntervalUsageCode.FecCodewordLength
                 non-defaults: [is_rcp_readonly: True]";
        }

        leaf PreambleLen {
            tlv:id 5;
            type uint16;
            units "bits";
            description
                "TLV [65.10.5]: UsScQamChannelConfig.IntervalUsageCode.PreambleLen
                 non-defaults: [is_rcp_readonly: True]";
        }

        leaf PreambleOffset {
            tlv:id 6;
            type uint16;
            units "bits";
            description
                "TLV [65.10.6]: UsScQamChannelConfig.IntervalUsageCode.PreambleOffset
                 non-defaults: [is_rcp_readonly: True]";
        }

        leaf PreambleModType {
            tlv:id 7;
            tlv:repr uint8;
            type enumeration {
                enum QPSK0  { value  1; description ""; }
                enum QPSK1  { value  2; description ""; }
            }
            description
                "TLV [65.10.7]: UsScQamChannelConfig.IntervalUsageCode.PreambleModType
                 non-defaults: [is_rcp_readonly: True]";
        }

        leaf Scrambler {
            tlv:id 8;
            type boolean;
            description
                "TLV [65.10.8]: UsScQamChannelConfig.IntervalUsageCode.Scrambler
                 non-defaults: [is_rcp_readonly: True]";
        }

        leaf ScramblerSeed {
            tlv:id 9;
            type uint16;
            description
                "TLV [65.10.9]: UsScQamChannelConfig.IntervalUsageCode.ScramblerSeed
                 non-defaults: [is_rcp_readonly: True]";
        }

        leaf MaxBurstSize {
            tlv:id 10;
            type uint8;
            description
                "TLV [65.10.10]: UsScQamChannelConfig.IntervalUsageCode.MaxBurstSize
                 non-defaults: [is_rcp_readonly: True]";
        }

        leaf LastCodewordShortened {
            tlv:id 11;
            type boolean;
            description
                "TLV [65.10.11]: UsScQamChannelConfig.IntervalUsageCode.LastCodewordShortened
                 non-defaults: [is_rcp_readonly: True]";
        }

        leaf ByteInterleaverDepth {
            tlv:id 12;
            type uint8;
            description
                "TLV [65.10.12]: UsScQamChannelConfig.IntervalUsageCode.ByteInterleaverDepth
                 non-defaults: [is_rcp_readonly: True]";
        }

        leaf ByteInterleaverBlockSize {
            tlv:id 13;
            type uint16;
            description
                "TLV [65.10.13]: UsScQamChannelConfig.IntervalUsageCode.ByteInterleaverBlockSize
                 non-defaults: [is_rcp_readonly: True]";
        }

        leaf ModulationType {
            tlv:id 14;
            tlv:repr uint8;
            type enumeration {
                enum other  { value  1; description ""; }
                enum QPSK   { value  2; description ""; }
                enum QAM8   { value  3; description ""; }
                enum QAM16  { value  4; description ""; }
                enum QAM32  { value  5; description ""; }
                enum QAM64  { value  6; description ""; }
                enum QAM128 { value  7; description ""; }
            }
            description
                "TLV [65.10.14]: UsScQamChannelConfig.IntervalUsageCode.ModulationType
                 non-defaults: [is_rcp_readonly: True]";
        }

        leaf GuardTime {
            tlv:id 15;
            type uint8;
            description
                "TLV [65.10.15]: UsScQamChannelConfig.IntervalUsageCode.GuardTime
                 non-defaults: [is_rcp_readonly: True]";
        }

    }  // g-IntervalUsageCode grouping

}
