module ucd-refresh-status-ofdma-module {
    yang-version 1;
    /* This file is automatically generated with Falcon V System's script.
       Any change made to this file will be lost. */

    namespace "falconvsystems:r-phy-10:ucd-refresh-status-ofdma-module";
    prefix "p-ucd-refresh-status-ofdma";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UcdRefreshStatusOfdma {
        tlv:id 10;
        description
            "TLV [79.10]: UsOfdmaChannelPerf.UcdRefreshStatusOfdma
             non-defaults: [is_rcp_readonly: True, is_readonly: True]";

        leaf UcdRefreshRequestOfdma {
            tlv:id 1;
            type boolean;
            description
                "TLV [79.10.1]: UsOfdmaChannelPerf.UcdRefreshStatusOfdma.UcdRefreshRequestOfdma
                 non-defaults: [is_rcp_readonly: True, is_readonly: True]";
        }

        leaf UcdRefreshReasonOfdma {
            tlv:id 2;
            type string;
            description
                "TLV [79.10.2]: UsOfdmaChannelPerf.UcdRefreshStatusOfdma.UcdRefreshReasonOfdma
                 non-defaults: [is_rcp_readonly: True, is_readonly: True]";
        }

    }  // g-UcdRefreshStatusOfdma grouping

}
