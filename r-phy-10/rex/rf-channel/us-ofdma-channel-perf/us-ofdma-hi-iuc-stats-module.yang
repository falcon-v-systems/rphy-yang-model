module us-ofdma-hi-iuc-stats-module {
    yang-version 1;
    /* This file is automatically generated with Falcon V System's script.
       Any change made to this file will be lost. */

    namespace "falconvsystems:r-phy-10:us-ofdma-hi-iuc-stats-module";
    prefix "p-us-ofdma-hi-iuc-stats";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UsOfdmaHiIucStats {
        tlv:id 2;
        description "TLV [79.2]: UsOfdmaChannelPerf.UsOfdmaHiIucStats";

        leaf UsIuc {
            tlv:id 1;
            tlv:repr uint8;
            type enumeration {
                enum 4  { value  4; description ""; }
                enum 5  { value  5; description ""; }
                enum 6  { value  6; description ""; }
                enum 9  { value  9; description ""; }
                enum 10 { value 10; description ""; }
                enum 11 { value 11; description ""; }
                enum 12 { value 12; description ""; }
                enum 13 { value 13; description ""; }
            }
            description "TLV [79.2.1]: UsOfdmaChannelPerf.UsOfdmaHiIucStats.UsIuc";
        }

        leaf ScheduledGrants {
            tlv:id 2;
            type uint64;
            description
                "TLV [79.2.2]: UsOfdmaChannelPerf.UsOfdmaHiIucStats.ScheduledGrants
                 non-defaults: [is_rcp_readonly: True, is_readonly: True]";
        }

        leaf NoEnergyBursts {
            tlv:id 3;
            type uint64;
            description
                "TLV [79.2.3]: UsOfdmaChannelPerf.UsOfdmaHiIucStats.NoEnergyBursts
                 non-defaults: [is_rcp_readonly: True, is_readonly: True]";
        }

        leaf NoPreambleBursts {
            tlv:id 4;
            type uint64;
            description
                "TLV [79.2.4]: UsOfdmaChannelPerf.UsOfdmaHiIucStats.NoPreambleBursts
                 non-defaults: [is_rcp_readonly: True, is_readonly: True]";
        }

        leaf ErrorBursts {
            tlv:id 5;
            type uint64;
            description
                "TLV [79.2.5]: UsOfdmaChannelPerf.UsOfdmaHiIucStats.ErrorBursts
                 non-defaults: [is_rcp_readonly: True, is_readonly: True]";
        }

        leaf NumPredecodePass {
            tlv:id 6;
            type uint64;
            description
                "TLV [79.2.6]: UsOfdmaChannelPerf.UsOfdmaHiIucStats.NumPredecodePass
                 non-defaults: [is_rcp_readonly: True, is_readonly: True]";
        }

        leaf NumPostdecodePass {
            tlv:id 7;
            type uint64;
            description
                "TLV [79.2.7]: UsOfdmaChannelPerf.UsOfdmaHiIucStats.NumPostdecodePass
                 non-defaults: [is_rcp_readonly: True, is_readonly: True]";
        }

        leaf NumPostdecodeFail {
            tlv:id 8;
            type uint64;
            description
                "TLV [79.2.8]: UsOfdmaChannelPerf.UsOfdmaHiIucStats.NumPostdecodeFail
                 non-defaults: [is_rcp_readonly: True, is_readonly: True]";
        }

        leaf AverageMer {
            tlv:id 9;
            type uint16;
            description
                "TLV [79.2.9]: UsOfdmaChannelPerf.UsOfdmaHiIucStats.AverageMer
                 non-defaults: [is_rcp_readonly: True, is_readonly: True]";
        }

    }  // g-UsOfdmaHiIucStats grouping

}
