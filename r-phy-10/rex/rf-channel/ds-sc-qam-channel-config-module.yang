module ds-sc-qam-channel-config-module {
    yang-version 1;
    /* This file is automatically generated with Falcon V System's script.
       Any change made to this file will be lost. */

    namespace "falconvsystems:r-phy-10:ds-sc-qam-channel-config-module";
    prefix "p-ds-sc-qam-channel-config";

    // --- imports ---------------------------------------

    import ietf-yang-types {
        prefix "yang";
        /*  External YANG module. */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-DsScQamChannelConfig {
        tlv:id 62;
        description "TLV [62]: DsScQamChannelConfig";

        leaf Index {
            // no tlv:id given
            type uint16;
            description
                "TLV [62.X]: DsScQamChannelConfig.Index
                 non-defaults: [is_key: True]";
        }

        leaf AdminState {
            tlv:id 1;
            tlv:repr uint8;
            type enumeration {
                enum other      { value  1; description ""; }
                enum up         { value  2; description ""; }
                enum down       { value  3; description ""; }
                enum testing    { value  4; description ""; }
            }
            description "TLV [62.1]: DsScQamChannelConfig.AdminState";
        }

        leaf CcapCoreOwner {
            tlv:id 2;
            type yang:mac-address;
            description "TLV [62.2]: DsScQamChannelConfig.CcapCoreOwner";
        }

        leaf RfMute {
            tlv:id 3;
            type boolean;
            description "TLV [62.3]: DsScQamChannelConfig.RfMute";
        }

        leaf TSID {
            tlv:id 4;
            type uint16;
            description "TLV [62.4]: DsScQamChannelConfig.TSID";
        }

        leaf CenterFrequency {
            tlv:id 5;
            type uint32;
            units "Hz";
            description "TLV [62.5]: DsScQamChannelConfig.CenterFrequency";
        }

        leaf OperationalMode {
            tlv:id 6;
            tlv:repr uint8;
            type enumeration {
                enum Other      { value  1; description ""; }
                enum DOCSIS     { value  2; description ""; }
                enum Sync_MPEG  { value  3; description ""; }
                enum Async_MPEG { value  4; description ""; }
                enum CW_carrier { value  5; description ""; }
            }
            description "TLV [62.6]: DsScQamChannelConfig.OperationalMode";
        }

        leaf Modulation {
            tlv:id 7;
            tlv:repr uint8;
            type enumeration {
                enum Unknown    { value  1; description ""; }
                enum Other      { value  2; description ""; }
                enum QAM_64     { value  3; description ""; }
                enum QAM_256    { value  4; description ""; }
            }
            description "TLV [62.7]: DsScQamChannelConfig.Modulation";
        }

        leaf InterleaverDepth {
            tlv:id 8;
            tlv:repr uint8;
            type enumeration {
                enum unknown            { value  1; description ""; }
                enum other              { value  2; description ""; }
                enum taps8Increment16   { value  3; description ""; }
                enum taps16Increment8   { value  4; description ""; }
                enum taps32Increment4   { value  5; description ""; }
                enum taps64Increment2   { value  6; description ""; }
                enum taps128Increment1  { value  7; description ""; }
                enum taps12Increment17  { value  8; description ""; }
            }
            description "TLV [62.8]: DsScQamChannelConfig.InterleaverDepth";
        }

        leaf Annex {
            tlv:id 9;
            tlv:repr uint8;
            type enumeration {
                enum Unknown    { value  1; description ""; }
                enum Other      { value  2; description ""; }
                enum A          { value  3; description ""; }
                enum B          { value  4; description ""; }
                enum C          { value  5; description ""; }
            }
            description "TLV [62.9]: DsScQamChannelConfig.Annex";
        }

        leaf SyncInterval {
            tlv:id 10;
            type uint8;
            units "Miliseconds";
            description "TLV [62.10]: DsScQamChannelConfig.SyncInterval";
        }

        leaf SyncMacAddress {
            tlv:id 11;
            type yang:mac-address;
            description "TLV [62.11]: DsScQamChannelConfig.SyncMacAddress";
        }

        leaf SymbolFrequencyDenominator {
            tlv:id 12;
            type uint16;
            description "TLV [62.12]: DsScQamChannelConfig.SymbolFrequencyDenominator";
        }

        leaf SymbolFrequencyNumerator {
            tlv:id 13;
            type uint16;
            description "TLV [62.13]: DsScQamChannelConfig.SymbolFrequencyNumerator";
        }

        leaf SymbolRateOverride {
            tlv:id 14;
            type uint32;
            description "TLV [62.14]: DsScQamChannelConfig.SymbolRateOverride";
        }

        leaf SpectrumInversionEnabled {
            tlv:id 15;
            type boolean;
            description "TLV [62.15]: DsScQamChannelConfig.SpectrumInversionEnabled";
        }

        leaf PowerAdjust {
            tlv:id 16;
            type int16;
            units "TenthdB";
            description "TLV [62.16]: DsScQamChannelConfig.PowerAdjust";
        }

    }  // g-DsScQamChannelConfig grouping

}
