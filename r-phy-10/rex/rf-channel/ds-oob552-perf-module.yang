module ds-oob552-perf-module {
    yang-version 1;
    /* This file is automatically generated with Falcon V System's script.
       Any change made to this file will be lost. */

    namespace "falconvsystems:r-phy-10:ds-oob552-perf-module";
    prefix "p-ds-oob552-perf";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-DsOob552Perf {
        tlv:id 75;
        description
            "TLV [75]: DsOob552Perf
             non-defaults: [is_rcp_readonly: True, is_readonly: True]";

        leaf outDiscards {
            tlv:id 1;
            type uint64;
            units "packets";
            description
                "TLV [75.1]: DsOob552Perf.outDiscards
                 non-defaults: [is_rcp_readonly: True, is_readonly: True]";
        }

        leaf outErrors {
            tlv:id 2;
            type uint64;
            units "packets";
            description
                "TLV [75.2]: DsOob552Perf.outErrors
                 non-defaults: [is_rcp_readonly: True, is_readonly: True]";
        }

        leaf outPackets {
            tlv:id 3;
            type uint64;
            units "packets";
            description
                "TLV [75.3]: DsOob552Perf.outPackets
                 non-defaults: [is_rcp_readonly: True, is_readonly: True]";
        }

        leaf discontinuityTime {
            tlv:id 4;
            type binary;
            description
                "TLV [75.4]: DsOob552Perf.discontinuityTime
                 non-defaults: [is_rcp_readonly: True, is_readonly: True]";
        }

        leaf operStatusDsOob552 {
            tlv:id 5;
            tlv:repr uint8;
            type enumeration {
                enum up     { value  1; description ""; }
                enum down   { value  2; description ""; }
            }
            description
                "TLV [75.5]: DsOob552Perf.operStatusDsOob552
                 non-defaults: [is_rcp_readonly: True, is_readonly: True]";
        }

    }  // g-DsOob552Perf grouping

}
