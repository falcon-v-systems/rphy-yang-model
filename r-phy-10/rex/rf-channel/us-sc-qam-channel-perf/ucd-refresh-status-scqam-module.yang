module ucd-refresh-status-scqam-module {
    yang-version 1;
    /* This file is automatically generated with Falcon V System's script.
       Any change made to this file will be lost. */

    namespace "falconvsystems:r-phy-10:ucd-refresh-status-scqam-module";
    prefix "p-ucd-refresh-status-scqam";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UcdRefreshStatusScqam {
        tlv:id 10;
        description
            "TLV [78.10]: UsScQamChannelPerf.UcdRefreshStatusScqam
             non-defaults: [is_rcp_readonly: True, is_readonly: True]";

        leaf UcdRefreshRequestScqam {
            tlv:id 1;
            type boolean;
            description
                "TLV [78.10.1]: UsScQamChannelPerf.UcdRefreshStatusScqam.UcdRefreshRequestScqam
                 non-defaults: [is_rcp_readonly: True, is_readonly: True]";
        }

        leaf UcdRefreshReasonScqam {
            tlv:id 2;
            type string;
            description
                "TLV [78.10.2]: UsScQamChannelPerf.UcdRefreshStatusScqam.UcdRefreshReasonScqam
                 non-defaults: [is_rcp_readonly: True, is_readonly: True]";
        }

    }  // g-UcdRefreshStatusScqam grouping

}
