module us-sc-qam-channel-perf-module {
    yang-version 1;
    /* This file is automatically generated with Falcon V System's script.
       Any change made to this file will be lost. */

    namespace "falconvsystems:r-phy-10:us-sc-qam-channel-perf-module";
    prefix "p-us-sc-qam-channel-perf";

    // --- imports ---------------------------------------

    import tlv-extension {
        prefix "tlv";
        /*  Falcon's Yang extension for TLV attributes. */
    }

    import ucd-refresh-status-scqam-module {
        prefix "p-ucd-refresh-status-scqam";
        /*  File path: rex/rf-channel/us-sc-qam-channel-perf/ucd-refresh-status-scqam-module.yang
            https://github.com/falcon-v-systems/rphy-yang-model/blob/master/r-phy-10/rex/rf-channel/us-sc-qam-channel-perf/ucd-refresh-status-scqam-module.yang */
    }

    import us-sc-chan-hi-iuc-stats-module {
        prefix "p-us-sc-chan-hi-iuc-stats";
        /*  File path: rex/rf-channel/us-sc-qam-channel-perf/us-sc-chan-hi-iuc-stats-module.yang
            https://github.com/falcon-v-systems/rphy-yang-model/blob/master/r-phy-10/rex/rf-channel/us-sc-qam-channel-perf/us-sc-chan-hi-iuc-stats-module.yang */
    }

    import us-sc-chan-low-iuc-stats-module {
        prefix "p-us-sc-chan-low-iuc-stats";
        /*  File path: rex/rf-channel/us-sc-qam-channel-perf/us-sc-chan-low-iuc-stats-module.yang
            https://github.com/falcon-v-systems/rphy-yang-model/blob/master/r-phy-10/rex/rf-channel/us-sc-qam-channel-perf/us-sc-chan-low-iuc-stats-module.yang */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UsScQamChannelPerf {
        tlv:id 78;
        description
            "TLV [78]: UsScQamChannelPerf
             non-defaults: [is_rcp_readonly: True, is_readonly: True]";

        leaf Index {
            // no tlv:id given
            type uint16;
            description
                "TLV [78.X]: UsScQamChannelPerf.Index
                 non-defaults: [is_key: True]";
        }

        container UsScChanLowIucStats {
            tlv:id 1;
            description "TLV [78.1]: UsScQamChannelPerf.UsScChanLowIucStats";
            uses "p-us-sc-chan-low-iuc-stats:g-UsScChanLowIucStats";
        }

        container UsScChanHiIucStats {
            tlv:id 2;
            description "TLV [78.2]: UsScQamChannelPerf.UsScChanHiIucStats";
            uses "p-us-sc-chan-hi-iuc-stats:g-UsScChanHiIucStats";
        }

        leaf HcsErrors {
            tlv:id 3;
            type uint64;
            description
                "TLV [78.3]: UsScQamChannelPerf.HcsErrors
                 non-defaults: [is_rcp_readonly: True, is_readonly: True]";
        }

        leaf LateMaps {
            tlv:id 4;
            type uint64;
            description
                "TLV [78.4]: UsScQamChannelPerf.LateMaps
                 non-defaults: [is_rcp_readonly: True, is_readonly: True]";
        }

        leaf IllegalMaps {
            tlv:id 5;
            type uint64;
            description
                "TLV [78.5]: UsScQamChannelPerf.IllegalMaps
                 non-defaults: [is_rcp_readonly: True, is_readonly: True]";
        }

        leaf DiscardedRequests {
            tlv:id 6;
            type uint64;
            description
                "TLV [78.6]: UsScQamChannelPerf.DiscardedRequests
                 non-defaults: [is_rcp_readonly: True, is_readonly: True]";
        }

        leaf ChannelSnr {
            tlv:id 7;
            type uint16;
            description
                "TLV [78.7]: UsScQamChannelPerf.ChannelSnr
                 non-defaults: [is_rcp_readonly: True, is_readonly: True]";
        }

        leaf discontinuityTime {
            tlv:id 8;
            type binary;
            description
                "TLV [78.8]: UsScQamChannelPerf.discontinuityTime
                 non-defaults: [is_rcp_readonly: True, is_readonly: True]";
        }

        leaf operStatusUsScQam {
            tlv:id 9;
            tlv:repr uint8;
            type enumeration {
                enum up     { value  1; description ""; }
                enum down   { value  2; description ""; }
            }
            description
                "TLV [78.9]: UsScQamChannelPerf.operStatusUsScQam
                 non-defaults: [is_rcp_readonly: True, is_readonly: True]";
        }

        container UcdRefreshStatusScqam {
            tlv:id 10;
            description
                "TLV [78.10]: UsScQamChannelPerf.UcdRefreshStatusScqam
                 non-defaults: [is_rcp_readonly: True, is_readonly: True]";
            uses "p-ucd-refresh-status-scqam:g-UcdRefreshStatusScqam";
        }

    }  // g-UsScQamChannelPerf grouping

}
