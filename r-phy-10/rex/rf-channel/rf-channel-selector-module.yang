module rf-channel-selector-module {
    yang-version 1;
    /* This file is automatically generated with Falcon V System's script.
       Any change made to this file will be lost. */

    namespace "falconvsystems:r-phy-10:rf-channel-selector-module";
    prefix "p-rf-channel-selector";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-RfChannelSelector {
        tlv:id 12;
        description "TLV [12]: RfChannelSelector";

        leaf RfPortIndex {
            tlv:id 1;
            type uint8;
            description "TLV [12.1]: RfChannelSelector.RfPortIndex";
        }

        leaf RfChannelType {
            tlv:id 2;
            tlv:repr uint8;
            type enumeration {
                enum DsScQam    { value  1; description ""; }
                enum DsOfdm     { value  2; description ""; }
                enum Ndf        { value  3; description ""; }
                enum DsScte55d1 { value  4; description ""; }
                enum UsAtdma    { value  5; description ""; }
                enum UsOfdma    { value  6; description ""; }
                enum reserved   { value  7; description ""; }
                enum Ndr        { value  8; description ""; }
                enum UsScte55d1 { value  9; description ""; }
                enum DsScto55d2 { value 10; description ""; }
                enum UsScte55d2 { value 11; description ""; }
            }
            description "TLV [12.2]: RfChannelSelector.RfChannelType";
        }

        leaf RfChannelIndex {
            tlv:id 3;
            type uint8;
            description "TLV [12.3]: RfChannelSelector.RfChannelIndex";
        }

        leaf Oob55d2ModuleIndex {
            tlv:id 4;
            type uint8;
            description "TLV [12.4]: RfChannelSelector.Oob55d2ModuleIndex";
        }

        leaf Oob55d2DemodIndex {
            tlv:id 5;
            type uint8;
            description "TLV [12.5]: RfChannelSelector.Oob55d2DemodIndex";
        }

    }  // g-RfChannelSelector grouping

}
