module ds-ofdm-subcarrier-modulation-module {
    yang-version 1;
    /* This file is automatically generated with Falcon V System's script.
       Any change made to this file will be lost. */

    namespace "falconvsystems:r-phy-10:ds-ofdm-subcarrier-modulation-module";
    prefix "p-ds-ofdm-subcarrier-modulation";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-DsOfdmSubcarrierModulation {
        tlv:id 2;
        description "TLV [64.2]: DsOfdmProfile.DsOfdmSubcarrierModulation";

        leaf StartSubcarrierId {
            tlv:id 1;
            type uint16;
            description
                "TLV [64.2.1]: DsOfdmProfile.DsOfdmSubcarrierModulation.StartSubcarrierId
                 non-defaults: [is_key: True]";
        }

        leaf EndSubcarrierId {
            tlv:id 2;
            type uint16;
            description
                "TLV [64.2.2]: DsOfdmProfile.DsOfdmSubcarrierModulation.EndSubcarrierId";
        }

        leaf Modulation {
            tlv:id 3;
            tlv:repr uint8;
            type enumeration {
                enum Zero       { value  2; description ""; }
                enum QPSK       { value  3; description ""; }
                enum QAM_16     { value  4; description ""; }
                enum QAM_64     { value  5; description ""; }
                enum QAM_128    { value  6; description ""; }
                enum QAM_256    { value  7; description ""; }
                enum QAM_512    { value  8; description ""; }
                enum QAM_1024   { value  9; description ""; }
                enum QAM_2048   { value 10; description ""; }
                enum QAM_4096   { value 11; description ""; }
                enum QAM_8192   { value 12; description ""; }
                enum QAM_16384  { value 13; description ""; }
            }
            description
                "TLV [64.2.3]: DsOfdmProfile.DsOfdmSubcarrierModulation.Modulation";
        }

    }  // g-DsOfdmSubcarrierModulation grouping

}
