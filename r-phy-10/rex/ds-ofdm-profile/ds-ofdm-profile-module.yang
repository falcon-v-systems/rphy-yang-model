module ds-ofdm-profile-module {
    yang-version 1;
    /* This file is automatically generated with Falcon V System's script.
       Any change made to this file will be lost. */

    namespace "falconvsystems:r-phy-10:ds-ofdm-profile-module";
    prefix "p-ds-ofdm-profile";

    // --- imports ---------------------------------------

    import ds-ofdm-subcarrier-modulation-module {
        prefix "p-ds-ofdm-subcarrier-modulation";
        /*  File path: rex/ds-ofdm-profile/ds-ofdm-subcarrier-modulation-module.yang
            https://github.com/falcon-v-systems/rphy-yang-model/blob/master/r-phy-10/rex/ds-ofdm-profile/ds-ofdm-subcarrier-modulation-module.yang */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-DsOfdmProfile {
        tlv:id 64;
        description "TLV [64]: DsOfdmProfile";

        leaf ProfileId {
            tlv:id 1;
            type uint8;
            description
                "TLV [64.1]: DsOfdmProfile.ProfileId
                 non-defaults: [is_key: True]";
        }

        list DsOfdmSubcarrierModulation {
            tlv:id 2;
            key "StartSubcarrierId";
            description "TLV [64.2]: DsOfdmProfile.DsOfdmSubcarrierModulation";
            uses "p-ds-ofdm-subcarrier-modulation:g-DsOfdmSubcarrierModulation";
        }

    }  // g-DsOfdmProfile grouping

}
