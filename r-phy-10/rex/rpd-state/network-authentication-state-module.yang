module network-authentication-state-module {
    yang-version 1;
    /* This file is automatically generated with Falcon V System's script.
       Any change made to this file will be lost. */

    namespace "falconvsystems:r-phy-10:network-authentication-state-module";
    prefix "p-network-authentication-state";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-NetworkAuthenticationState {
        tlv:id 2;
        description
            "TLV [87.2]: RpdState.NetworkAuthenticationState
             non-defaults: [is_rcp_readonly: True, is_readonly: True]";

        leaf NetworkAuthenticationPortIndex {
            tlv:id 1;
            type uint8;
            description
                "TLV [87.2.1]: RpdState.NetworkAuthenticationState.NetworkAuthenticationPortIndex
                 non-defaults: [is_key: True, is_rcp_readonly: True, is_readonly: True]";
        }

        leaf NetworkAuthenticationRpdState {
            tlv:id 2;
            tlv:repr uint8;
            type enumeration {
                enum WaitForEapReq              { value  1; description ""; }
                enum Execute802_1x              { value  2; description ""; }
                enum SleepAfterFailure          { value  3; description ""; }
                enum OperationalAuthenticated   { value  4; description ""; }
                enum OperationalNotAuthenticate { value  5; description ""; }
            }
            description
                "TLV [87.2.2]: RpdState.NetworkAuthenticationState.NetworkAuthenticationRpdState
                 non-defaults: [is_rcp_readonly: True, is_readonly: True]";
        }

    }  // g-NetworkAuthenticationState grouping

}
