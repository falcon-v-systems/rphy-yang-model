module us-sc-qam-profile-response-module {
    yang-version 1;
    /* This file is automatically generated with Falcon V System's script.
       Any change made to this file will be lost. */

    namespace "falconvsystems:r-phy-10:us-sc-qam-profile-response-module";
    prefix "p-us-sc-qam-profile-response";

    // --- imports ---------------------------------------

    import response-iuc-code-module {
        prefix "p-response-iuc-code";
        /*  File path: rex/us-sc-qam-profile-response/response-iuc-code-module.yang
            https://github.com/falcon-v-systems/rphy-yang-model/blob/master/r-phy-10/rex/us-sc-qam-profile-response/response-iuc-code-module.yang */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UsScQamProfileResponse {
        tlv:id 151;
        description
            "TLV [151]: UsScQamProfileResponse
             non-defaults: [is_rcp_readonly: True]";

        leaf ResponseScQamPreambleString {
            tlv:id 1;
            type binary;
            description
                "TLV [151.1]: UsScQamProfileResponse.ResponseScQamPreambleString
                 non-defaults: [is_rcp_readonly: True]";
        }

        container ResponseIucCode {
            tlv:id 2;
            description
                "TLV [151.2]: UsScQamProfileResponse.ResponseIucCode
                 non-defaults: [is_rcp_readonly: True]";
            uses "p-response-iuc-code:g-ResponseIucCode";
        }

    }  // g-UsScQamProfileResponse grouping

}
