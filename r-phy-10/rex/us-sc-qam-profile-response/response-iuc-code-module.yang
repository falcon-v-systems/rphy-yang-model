module response-iuc-code-module {
    yang-version 1;
    /* This file is automatically generated with Falcon V System's script.
       Any change made to this file will be lost. */

    namespace "falconvsystems:r-phy-10:response-iuc-code-module";
    prefix "p-response-iuc-code";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-ResponseIucCode {
        tlv:id 2;
        description
            "TLV [151.2]: UsScQamProfileResponse.ResponseIucCode
             non-defaults: [is_rcp_readonly: True]";

        leaf ResponseScQamCode {
            tlv:id 1;
            type uint8;
            description
                "TLV [151.2.1]: UsScQamProfileResponse.ResponseIucCode.ResponseScQamCode
                 non-defaults: [is_rcp_readonly: True]";
        }

        leaf ResponseScQamPreambleLen {
            tlv:id 2;
            type uint16;
            description
                "TLV [151.2.2]: UsScQamProfileResponse.ResponseIucCode.ResponseScQamPreambleLen
                 non-defaults: [is_rcp_readonly: True]";
        }

        leaf ResponseScQamPreambleOffset {
            tlv:id 3;
            type uint16;
            description
                "TLV [151.2.3]: UsScQamProfileResponse.ResponseIucCode.ResponseScQamPreambleOffset
                 non-defaults: [is_rcp_readonly: True]";
        }

        leaf ResponseScQamPreambleModType {
            tlv:id 4;
            tlv:repr uint8;
            type enumeration {
                enum QPSK0  { value  1; description ""; }
                enum QPSK1  { value  2; description ""; }
            }
            description
                "TLV [151.2.4]: UsScQamProfileResponse.ResponseIucCode.ResponseScQamPreambleModType
                 non-defaults: [is_rcp_readonly: True]";
        }

        leaf ResponseScQamScramblerSeed {
            tlv:id 5;
            type uint16;
            description
                "TLV [151.2.5]: UsScQamProfileResponse.ResponseIucCode.ResponseScQamScramblerSeed
                 non-defaults: [is_rcp_readonly: True]";
        }

        leaf ResponseScQamGuardTime {
            tlv:id 6;
            type uint8;
            description
                "TLV [151.2.6]: UsScQamProfileResponse.ResponseIucCode.ResponseScQamGuardTime
                 non-defaults: [is_rcp_readonly: True]";
        }

    }  // g-ResponseIucCode grouping

}
