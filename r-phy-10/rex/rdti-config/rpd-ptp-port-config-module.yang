module rpd-ptp-port-config-module {
    yang-version 1;
    /* This file is automatically generated with Falcon V System's script.
       Any change made to this file will be lost. */

    namespace "falconvsystems:r-phy-10:rpd-ptp-port-config-module";
    prefix "p-rpd-ptp-port-config";

    // --- imports ---------------------------------------

    import ietf-inet-types {
        prefix "inet";
        /*  External YANG module. */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-RpdPtpPortConfig {
        tlv:id 8;
        description "TLV [97.8]: RdtiConfig.RpdPtpPortConfig";

        leaf RpdEnetPortIndex {
            tlv:id 1;
            type uint16;
            description
                "TLV [97.8.1]: RdtiConfig.RpdPtpPortConfig.RpdEnetPortIndex
                 non-defaults: [is_key: True]";
        }

        leaf RpdPtpPortIndex {
            tlv:id 2;
            type uint16;
            description
                "TLV [97.8.2]: RdtiConfig.RpdPtpPortConfig.RpdPtpPortIndex
                 non-defaults: [is_key: True]";
        }

        leaf RpdPtpPortAdminState {
            tlv:id 3;
            tlv:repr uint8;
            type enumeration {
                enum other      { value  1; description ""; }
                enum up         { value  2; description ""; }
                enum down       { value  3; description ""; }
                enum testing    { value  4; description ""; }
            }
            description
                "TLV [97.8.3]: RdtiConfig.RpdPtpPortConfig.RpdPtpPortAdminState";
        }

        leaf RpdPtpPortClockSource {
            tlv:id 4;
            type inet:ip-address;
            description
                "TLV [97.8.4]: RdtiConfig.RpdPtpPortConfig.RpdPtpPortClockSource";
        }

        leaf RpdPtpPortClockAlternateSource {
            tlv:id 5;
            type inet:ip-address;
            description
                "TLV [97.8.5]: RdtiConfig.RpdPtpPortConfig.RpdPtpPortClockAlternateSource";
        }

        leaf RpdPtpPortClockSelectAlternateSourceFirst {
            tlv:id 6;
            type boolean;
            description
                "TLV [97.8.6]: RdtiConfig.RpdPtpPortConfig.RpdPtpPortClockSelectAlternateSourceFirst";
        }

        leaf RpdPtpPortTransportType {
            tlv:id 7;
            tlv:repr uint8;
            type enumeration {
                enum other  { value  1; description ""; }
                enum IPv4   { value  2; description ""; }
                enum IPv6   { value  3; description ""; }
            }
            description
                "TLV [97.8.7]: RdtiConfig.RpdPtpPortConfig.RpdPtpPortTransportType";
        }

        leaf RpdPtpPortTransportCos {
            tlv:id 8;
            type uint8;
            description
                "TLV [97.8.8]: RdtiConfig.RpdPtpPortConfig.RpdPtpPortTransportCos";
        }

        leaf RpdPtpPortTransportDscp {
            tlv:id 9;
            type uint8;
            description
                "TLV [97.8.9]: RdtiConfig.RpdPtpPortConfig.RpdPtpPortTransportDscp";
        }

        leaf RpdPtpPortDsLocalPriority {
            tlv:id 10;
            type uint8;
            description
                "TLV [97.8.10]: RdtiConfig.RpdPtpPortConfig.RpdPtpPortDsLocalPriority";
        }

        leaf RpdPtpPortDsLogSyncInterval {
            tlv:id 11;
            type int8;
            description
                "TLV [97.8.11]: RdtiConfig.RpdPtpPortConfig.RpdPtpPortDsLogSyncInterval";
        }

        leaf RpdPtpPortDsLogAnnounceInterval {
            tlv:id 12;
            type int8;
            description
                "TLV [97.8.12]: RdtiConfig.RpdPtpPortConfig.RpdPtpPortDsLogAnnounceInterval";
        }

        leaf RpdPtpPortDsLogDelayReqInterval {
            tlv:id 13;
            type int8;
            description
                "TLV [97.8.13]: RdtiConfig.RpdPtpPortConfig.RpdPtpPortDsLogDelayReqInterval";
        }

        leaf RpdPtpPortDsAnnounceReceiptTimeout {
            tlv:id 14;
            type uint8;
            units "seconds";
            description
                "TLV [97.8.14]: RdtiConfig.RpdPtpPortConfig.RpdPtpPortDsAnnounceReceiptTimeout";
        }

        leaf RpdPtpPortUnicastContractDuration {
            tlv:id 15;
            type uint16;
            units "seconds";
            description
                "TLV [97.8.15]: RdtiConfig.RpdPtpPortConfig.RpdPtpPortUnicastContractDuration";
        }

        leaf RpdPtpPortClockSrcGw {
            tlv:id 16;
            type inet:ip-address;
            description
                "TLV [97.8.16]: RdtiConfig.RpdPtpPortConfig.RpdPtpPortClockSrcGw";
        }

        leaf RpdPtpPortClockAltSrcGw {
            tlv:id 17;
            type inet:ip-address;
            description
                "TLV [97.8.17]: RdtiConfig.RpdPtpPortConfig.RpdPtpPortClockAltSrcGw";
        }

    }  // g-RpdPtpPortConfig grouping

}
