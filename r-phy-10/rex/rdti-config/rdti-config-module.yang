module rdti-config-module {
    yang-version 1;
    /* This file is automatically generated with Falcon V System's script.
       Any change made to this file will be lost. */

    namespace "falconvsystems:r-phy-10:rdti-config-module";
    prefix "p-rdti-config";

    // --- imports ---------------------------------------

    import ietf-yang-types {
        prefix "yang";
        /*  External YANG module. */
    }

    import rpd-ptp-port-config-module {
        prefix "p-rpd-ptp-port-config";
        /*  File path: rex/rdti-config/rpd-ptp-port-config-module.yang
            https://github.com/falcon-v-systems/rphy-yang-model/blob/master/r-phy-10/rex/rdti-config/rpd-ptp-port-config-module.yang */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-RdtiConfig {
        tlv:id 97;
        description "TLV [97]: RdtiConfig";

        leaf RpdRdtiMode {
            tlv:id 1;
            tlv:repr uint8;
            type enumeration {
                enum other          { value  1; description ""; }
                enum RpdNodeSlave   { value  2; description ""; }
                enum RpdNodeMaster  { value  3; description ""; }
            }
            description "TLV [97.1]: RdtiConfig.RpdRdtiMode";
        }

        leaf RpdPtpDefDsDomainNumber {
            tlv:id 2;
            type uint8;
            description "TLV [97.2]: RdtiConfig.RpdPtpDefDsDomainNumber";
        }

        leaf RpdPtpDefDsPriority1 {
            tlv:id 3;
            type uint8;
            description "TLV [97.3]: RdtiConfig.RpdPtpDefDsPriority1";
        }

        leaf RpdPtpDefDsPriority2 {
            tlv:id 4;
            type uint8;
            description "TLV [97.4]: RdtiConfig.RpdPtpDefDsPriority2";
        }

        leaf RpdPtpDefDsLocalPriority {
            tlv:id 5;
            type uint8;
            description "TLV [97.5]: RdtiConfig.RpdPtpDefDsLocalPriority";
        }

        leaf RpdPtpProfileIdentifier {
            tlv:id 6;
            type yang:mac-address;
            description "TLV [97.6]: RdtiConfig.RpdPtpProfileIdentifier";
        }

        leaf RpdPtpProfileVersion {
            tlv:id 7;
            type binary;
            description "TLV [97.7]: RdtiConfig.RpdPtpProfileVersion";
        }

        list RpdPtpPortConfig {
            tlv:id 8;
            key "RpdEnetPortIndex RpdPtpPortIndex";
            description "TLV [97.8]: RdtiConfig.RpdPtpPortConfig";
            uses "p-rpd-ptp-port-config:g-RpdPtpPortConfig";
        }

    }  // g-RdtiConfig grouping

}
