module rpd-backup-core-status-table-module {
    yang-version 1;
    /* This file is automatically generated with Falcon V System's script.
       Any change made to this file will be lost. */

    namespace "falconvsystems:r-phy-10:rpd-backup-core-status-table-module";
    prefix "p-rpd-backup-core-status-table";

    // --- imports ---------------------------------------

    import ietf-yang-types {
        prefix "yang";
        /*  External YANG module. */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-RpdBackupCoreStatusTable {
        tlv:id 107;
        description "TLV [107]: RpdBackupCoreStatusTable";

        leaf Index {
            tlv:id 1;
            type uint8;
            description
                "TLV [107.1]: RpdBackupCoreStatusTable.Index
                 non-defaults: [is_key: True]";
        }

        leaf CoreId {
            tlv:id 2;
            type yang:mac-address;
            description "TLV [107.2]: RpdBackupCoreStatusTable.CoreId";
        }

        leaf RpdGcpBackupCoreStatus {
            tlv:id 3;
            tlv:repr uint8;
            type enumeration {
                enum ContactPending     { value  1; description ""; }
                enum Active             { value  2; description ""; }
                enum Backup             { value  3; description ""; }
                enum NotActing          { value  4; description ""; }
                enum DecisionPending    { value  5; description ""; }
                enum Handover           { value  6; description ""; }
            }
            description "TLV [107.3]: RpdBackupCoreStatusTable.RpdGcpBackupCoreStatus";
        }

    }  // g-RpdBackupCoreStatusTable grouping

}
