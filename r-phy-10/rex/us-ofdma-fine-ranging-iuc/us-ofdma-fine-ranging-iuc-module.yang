module us-ofdma-fine-ranging-iuc-module {
    yang-version 1;
    /* This file is automatically generated with Falcon V System's script.
       Any change made to this file will be lost. */

    namespace "falconvsystems:r-phy-10:us-ofdma-fine-ranging-iuc-module";
    prefix "p-us-ofdma-fine-ranging-iuc";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UsOfdmaFineRangingIuc {
        tlv:id 68;
        description "TLV [68]: UsOfdmaFineRangingIuc";

        leaf NumSubcarriers {
            tlv:id 1;
            type uint16;
            description
                "TLV [68.1]: UsOfdmaFineRangingIuc.NumSubcarriers
                 non-defaults: [is_rcp_readonly: True]";
        }

        leaf Guardband {
            tlv:id 2;
            type uint16;
            description
                "TLV [68.2]: UsOfdmaFineRangingIuc.Guardband
                 non-defaults: [is_rcp_readonly: True]";
        }

    }  // g-UsOfdmaFineRangingIuc grouping

}
