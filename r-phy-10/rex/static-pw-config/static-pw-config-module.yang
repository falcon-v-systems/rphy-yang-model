module static-pw-config-module {
    yang-version 1;
    /* This file is automatically generated with Falcon V System's script.
       Any change made to this file will be lost. */

    namespace "falconvsystems:r-phy-10:static-pw-config-module";
    prefix "p-static-pw-config";

    // --- imports ---------------------------------------

    import common-static-pw-config-module {
        prefix "p-common-static-pw-config";
        /*  File path: rex/static-pw-config/common-static-pw-config/common-static-pw-config-module.yang
            https://github.com/falcon-v-systems/rphy-yang-model/blob/master/r-phy-10/rex/static-pw-config/common-static-pw-config/common-static-pw-config-module.yang */
    }

    import fwd-static-pw-config-module {
        prefix "p-fwd-static-pw-config";
        /*  File path: rex/static-pw-config/fwd-static-pw-config-module.yang
            https://github.com/falcon-v-systems/rphy-yang-model/blob/master/r-phy-10/rex/static-pw-config/fwd-static-pw-config-module.yang */
    }

    import ret-static-pw-config-module {
        prefix "p-ret-static-pw-config";
        /*  File path: rex/static-pw-config/ret-static-pw-config-module.yang
            https://github.com/falcon-v-systems/rphy-yang-model/blob/master/r-phy-10/rex/static-pw-config/ret-static-pw-config-module.yang */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-StaticPwConfig {
        tlv:id 58;
        description "TLV [58]: StaticPwConfig";

        container FwdStaticPwConfig {
            tlv:id 1;
            description "TLV [58.1]: StaticPwConfig.FwdStaticPwConfig";
            uses "p-fwd-static-pw-config:g-FwdStaticPwConfig";
        }

        container RetStaticPwConfig {
            tlv:id 2;
            description "TLV [58.2]: StaticPwConfig.RetStaticPwConfig";
            uses "p-ret-static-pw-config:g-RetStaticPwConfig";
        }

        list CommonStaticPwConfig {
            tlv:id 3;
            key "SessionId";
            description "TLV [58.3]: StaticPwConfig.CommonStaticPwConfig";
            uses "p-common-static-pw-config:g-CommonStaticPwConfig";
        }

    }  // g-StaticPwConfig grouping

}
