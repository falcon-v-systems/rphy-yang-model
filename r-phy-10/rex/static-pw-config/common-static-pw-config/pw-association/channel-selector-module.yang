module channel-selector-module {
    yang-version 1;
    /* This file is automatically generated with Falcon V System's script.
       Any change made to this file will be lost. */

    namespace "falconvsystems:r-phy-10:channel-selector-module";
    prefix "p-channel-selector";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-ChannelSelector {
        tlv:id 2;
        description
            "TLV [58.3.11.2]: StaticPwConfig.CommonStaticPwConfig.PwAssociation.ChannelSelector";

        leaf RfPortIndex {
            tlv:id 1;
            type uint8;
            description
                "TLV [58.3.11.2.1]: StaticPwConfig.CommonStaticPwConfig.PwAssociation.ChannelSelector.RfPortIndex";
        }

        leaf ChannelType {
            tlv:id 2;
            tlv:repr uint8;
            type enumeration {
                enum DsScQam        { value  3; description ""; }
                enum Scte55_1Fwd    { value  6; description ""; }
                enum Scte55_1Ret    { value  7; description ""; }
                enum NDF            { value 10; description ""; }
                enum NDR            { value 11; description ""; }
            }
            description
                "TLV [58.3.11.2.2]: StaticPwConfig.CommonStaticPwConfig.PwAssociation.ChannelSelector.ChannelType";
        }

        leaf ChannelIndex {
            tlv:id 3;
            type uint8;
            description
                "TLV [58.3.11.2.3]: StaticPwConfig.CommonStaticPwConfig.PwAssociation.ChannelSelector.ChannelIndex";
        }

    }  // g-ChannelSelector grouping

}
