module common-static-pw-config-module {
    yang-version 1;
    /* This file is automatically generated with Falcon V System's script.
       Any change made to this file will be lost. */

    namespace "falconvsystems:r-phy-10:common-static-pw-config-module";
    prefix "p-common-static-pw-config";

    // --- imports ---------------------------------------

    import pw-association-module {
        prefix "p-pw-association";
        /*  File path: rex/static-pw-config/common-static-pw-config/pw-association/pw-association-module.yang
            https://github.com/falcon-v-systems/rphy-yang-model/blob/master/r-phy-10/rex/static-pw-config/common-static-pw-config/pw-association/pw-association-module.yang */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-CommonStaticPwConfig {
        tlv:id 3;
        description "TLV [58.3]: StaticPwConfig.CommonStaticPwConfig";

        leaf Direction {
            tlv:id 1;
            tlv:repr uint8;
            type enumeration {
                enum ForwardDirPseudowire   { value  0; description ""; }
                enum ReturnDirPseudowire    { value  1; description ""; }
            }
            description "TLV [58.3.1]: StaticPwConfig.CommonStaticPwConfig.Direction";
        }

        leaf Index {
            tlv:id 2;
            type uint16;
            description
                "TLV [58.3.2]: StaticPwConfig.CommonStaticPwConfig.Index
                 non-defaults: [is_readonly: True]";
        }

        leaf PwType {
            tlv:id 4;
            tlv:repr uint16;
            type enumeration {
                enum MPT    { value 12; description ""; }
                enum PSP    { value 13; description ""; }
            }
            description "TLV [58.3.4]: StaticPwConfig.CommonStaticPwConfig.PwType";
        }

        leaf DepiPwSubtype {
            tlv:id 5;
            tlv:repr uint16;
            type enumeration {
                enum MPT_DEPI           { value  1; description ""; }
                enum PSP_LEGACY         { value  2; description ""; }
                enum MCM                { value  3; description ""; }
                enum PSP_MULTICHAN      { value  4; description ""; }
                enum PSP_UEPI_SCQ       { value  6; description ""; }
                enum PSP_UEPI_OFDMA     { value  7; description ""; }
                enum PSP_BW_REQ_SCQ     { value  8; description ""; }
                enum PSP_PBW_REQ_OFDMA  { value  9; description ""; }
                enum PSP_BW_PROBE       { value 10; description ""; }
                enum PSP_RNG_REQ_SCQ    { value 11; description ""; }
                enum PSP_RNG_REQ_OFDMA  { value 12; description ""; }
                enum PSP_MAP_SCQ        { value 13; description ""; }
                enum PSP_MAP_OFDMA      { value 14; description ""; }
                enum PSP_SPECMAN        { value 15; description ""; }
                enum PSP_PNM            { value 16; description ""; }
                enum MPT_55_1_RET       { value 18; description ""; }
                enum MPT_55_2_FWD       { value 19; description ""; }
                enum MPT_55_2_RET       { value 20; description ""; }
                enum PSP_NDF            { value 21; description ""; }
                enum PSP_NDR            { value 22; description ""; }
            }
            description
                "TLV [58.3.5]: StaticPwConfig.CommonStaticPwConfig.DepiPwSubtype";
        }

        leaf L2SublayerType {
            tlv:id 6;
            tlv:repr uint16;
            type enumeration {
                enum MPT_L2_SST { value  3; description ""; }
                enum PSP_L2_SST { value  4; description ""; }
            }
            description
                "TLV [58.3.6]: StaticPwConfig.CommonStaticPwConfig.L2SublayerType";
        }

        leaf DepiL2SublayerSubtype {
            tlv:id 7;
            tlv:repr uint16;
            type enumeration {
                enum MPT_DEPI_L2_SSS                { value  1; description ""; }
                enum PSP_Legacy_L2_SSS              { value  2; description ""; }
                enum MCM_L2_SSS                     { value  3; description ""; }
                enum PSP_DEPI_Multichannel_L2_SSS   { value  4; description ""; }
                enum PSP_UEPI_SCQAM_L2_SSS          { value  6; description ""; }
                enum PSP_UEPI_OFDMA_L2_SSS          { value  7; description ""; }
                enum PSP_BW_REQ_SCQ_L2_SSS          { value  8; description ""; }
                enum PSP_BW_REQ_OFDMA_L2_SSS        { value  9; description ""; }
                enum PSP_PROBE_L2_SSS               { value 10; description ""; }
                enum PSP_RNG_REQ_SCQ_L2_SSS         { value 11; description ""; }
                enum PSP_RNG_REQ_OFDMA_L2_SSS       { value 12; description ""; }
                enum PSP_MAP_SCQ_L2_SSS             { value 13; description ""; }
                enum PSP_MAP_OFDMA_L2_SSS           { value 14; description ""; }
                enum PSP_SPECMAN_L2_SSS             { value 15; description ""; }
                enum PSP_PNM_L2_SSS                 { value 16; description ""; }
                enum MPT_55_1_RET_L2_SSS            { value 18; description ""; }
                enum MPT_55_2_FWD_L2_SSS            { value 19; description ""; }
                enum MPT_55_2_RET_L2_SSS            { value 20; description ""; }
                enum PSP_NDF_L2_SSS                 { value 21; description ""; }
                enum PSP_NDR_L2_SSS                 { value 22; description ""; }
            }
            description
                "TLV [58.3.7]: StaticPwConfig.CommonStaticPwConfig.DepiL2SublayerSubtype";
        }

        leaf SessionId {
            tlv:id 8;
            type uint32;
            description
                "TLV [58.3.8]: StaticPwConfig.CommonStaticPwConfig.SessionId
                 non-defaults: [is_key: True]";
        }

        leaf CircuitStatus {
            tlv:id 9;
            type uint16;
            description
                "TLV [58.3.9]: StaticPwConfig.CommonStaticPwConfig.CircuitStatus";
        }

        leaf RpdEnetPortIndex {
            tlv:id 10;
            type uint8;
            description
                "TLV [58.3.10]: StaticPwConfig.CommonStaticPwConfig.RpdEnetPortIndex";
        }

        list PwAssociation {
            tlv:id 11;
            key "Index";
            description
                "TLV [58.3.11]: StaticPwConfig.CommonStaticPwConfig.PwAssociation";
            uses "p-pw-association:g-PwAssociation";
        }

        leaf EnableStatusNotification {
            tlv:id 12;
            type boolean;
            description
                "TLV [58.3.12]: StaticPwConfig.CommonStaticPwConfig.EnableStatusNotification";
        }

    }  // g-CommonStaticPwConfig grouping

}
