module fwd-static-pw-config-module {
    yang-version 1;
    /* This file is automatically generated with Falcon V System's script.
       Any change made to this file will be lost. */

    namespace "falconvsystems:r-phy-10:fwd-static-pw-config-module";
    prefix "p-fwd-static-pw-config";

    // --- imports ---------------------------------------

    import ietf-inet-types {
        prefix "inet";
        /*  External YANG module. */
    }

    import ietf-yang-types {
        prefix "yang";
        /*  External YANG module. */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-FwdStaticPwConfig {
        tlv:id 1;
        description "TLV [58.1]: StaticPwConfig.FwdStaticPwConfig";

        leaf Index {
            tlv:id 1;
            type uint16;
            description "TLV [58.1.1]: StaticPwConfig.FwdStaticPwConfig.Index";
        }

        leaf CcapCoreOwner {
            tlv:id 2;
            type yang:mac-address;
            description "TLV [58.1.2]: StaticPwConfig.FwdStaticPwConfig.CcapCoreOwner";
        }

        leaf GroupAddress {
            tlv:id 3;
            type inet:ip-address;
            description "TLV [58.1.3]: StaticPwConfig.FwdStaticPwConfig.GroupAddress";
        }

        leaf SourceAddress {
            tlv:id 4;
            type inet:ip-address;
            description "TLV [58.1.4]: StaticPwConfig.FwdStaticPwConfig.SourceAddress";
        }

    }  // g-FwdStaticPwConfig grouping

}
