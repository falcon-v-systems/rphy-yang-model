module us-ofdma-data-iuc-module {
    yang-version 1;
    /* This file is automatically generated with Falcon V System's script.
       Any change made to this file will be lost. */

    namespace "falconvsystems:r-phy-10:us-ofdma-data-iuc-module";
    prefix "p-us-ofdma-data-iuc";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UsOfdmaDataIuc {
        tlv:id 69;
        description "TLV [69]: UsOfdmaDataIuc";

        leaf DataIuc {
            tlv:id 1;
            tlv:repr uint8;
            type enumeration {
                enum  5 { value  5; description ""; }
                enum  6 { value  6; description ""; }
                enum  9 { value  9; description ""; }
                enum 10 { value 10; description ""; }
                enum 11 { value 11; description ""; }
                enum 12 { value 12; description ""; }
                enum 13 { value 13; description ""; }
            }
            description
                "TLV [69.1]: UsOfdmaDataIuc.DataIuc
                 non-defaults: [is_key: True]";
        }

        leaf StartMinislot {
            tlv:id 2;
            type uint8;
            description
                "TLV [69.2]: UsOfdmaDataIuc.StartMinislot
                 non-defaults: [is_rcp_readonly: True, is_readonly: True]";
        }

        leaf FirstSubcarrierId {
            tlv:id 3;
            type uint16;
            description
                "TLV [69.3]: UsOfdmaDataIuc.FirstSubcarrierId
                 non-defaults: [is_rcp_readonly: True, is_readonly: True]";
        }

        leaf NumConsecutiveMinislots {
            tlv:id 4;
            type uint8;
            description
                "TLV [69.4]: UsOfdmaDataIuc.NumConsecutiveMinislots
                 non-defaults: [is_rcp_readonly: True, is_readonly: True]";
        }

        leaf MinislotPilotPattern {
            tlv:id 5;
            type uint8;
            description
                "TLV [69.5]: UsOfdmaDataIuc.MinislotPilotPattern
                 non-defaults: [is_rcp_readonly: True, is_readonly: True]";
        }

        leaf DataSymbolModulation {
            tlv:id 6;
            tlv:repr uint8;
            type enumeration {
                enum other      { value  1; description ""; }
                enum zeroValued { value  2; description ""; }
                enum bpsk       { value  3; description ""; }
                enum qam8       { value  4; description ""; }
                enum qam16      { value  5; description ""; }
                enum qam32      { value  6; description ""; }
                enum qam74      { value  7; description ""; }
                enum qam128     { value  8; description ""; }
                enum qam256     { value  9; description ""; }
                enum qam512     { value 10; description ""; }
                enum qam1024    { value 11; description ""; }
                enum qam2048    { value 12; description ""; }
                enum qam4096    { value 13; description ""; }
            }
            description
                "TLV [69.6]: UsOfdmaDataIuc.DataSymbolModulation
                 non-defaults: [is_rcp_readonly: True, is_readonly: True]";
        }

    }  // g-UsOfdmaDataIuc grouping

}
