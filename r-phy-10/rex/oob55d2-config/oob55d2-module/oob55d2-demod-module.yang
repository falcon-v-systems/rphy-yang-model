module oob55d2-demod-module {
    yang-version 1;
    /* This file is automatically generated with Falcon V System's script.
       Any change made to this file will be lost. */

    namespace "falconvsystems:r-phy-10:oob55d2-demod-module";
    prefix "p-oob55d2-demod";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-Oob55d2Demod {
        tlv:id 10;
        description "TLV [93.4.10]: Oob55d2Config.Oob55d2Module.Oob55d2Demod";

        leaf DemodIndex {
            tlv:id 1;
            type uint8;
            description
                "TLV [93.4.10.1]: Oob55d2Config.Oob55d2Module.Oob55d2Demod.DemodIndex
                 non-defaults: [is_key: True]";
        }

        leaf UpstreamGroupId {
            tlv:id 2;
            type uint8;
            description
                "TLV [93.4.10.2]: Oob55d2Config.Oob55d2Module.Oob55d2Demod.UpstreamGroupId";
        }

        leaf MaxDhctDistance {
            tlv:id 3;
            type uint8;
            units "31km";
            description
                "TLV [93.4.10.3]: Oob55d2Config.Oob55d2Module.Oob55d2Demod.MaxDhctDistance";
        }

        leaf UsPortAssociation {
            tlv:id 4;
            type uint8;
            description
                "TLV [93.4.10.4]: Oob55d2Config.Oob55d2Module.Oob55d2Demod.UsPortAssociation
                 non-defaults: [is_rcp_readonly: True, is_readonly: True]";
        }

    }  // g-Oob55d2Demod grouping

}
