module oob55d2-module-module {
    yang-version 1;
    /* This file is automatically generated with Falcon V System's script.
       Any change made to this file will be lost. */

    namespace "falconvsystems:r-phy-10:oob55d2-module-module";
    prefix "p-oob55d2-module";

    // --- imports ---------------------------------------

    import oob55d2-demod-module {
        prefix "p-oob55d2-demod";
        /*  File path: rex/oob55d2-config/oob55d2-module/oob55d2-demod-module.yang
            https://github.com/falcon-v-systems/rphy-yang-model/blob/master/r-phy-10/rex/oob55d2-config/oob55d2-module/oob55d2-demod-module.yang */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-Oob55d2Module {
        tlv:id 4;
        description "TLV [93.4]: Oob55d2Config.Oob55d2Module";

        leaf ModuleIndex {
            tlv:id 1;
            type uint8;
            description
                "TLV [93.4.1]: Oob55d2Config.Oob55d2Module.ModuleIndex
                 non-defaults: [is_key: True]";
        }

        leaf ModulatorId {
            tlv:id 2;
            type uint8;
            description "TLV [93.4.2]: Oob55d2Config.Oob55d2Module.ModulatorId";
        }

        leaf ServiceChannelLastSlot {
            tlv:id 3;
            type uint16;
            description
                "TLV [93.4.3]: Oob55d2Config.Oob55d2Module.ServiceChannelLastSlot";
        }

        leaf DefaultRangingInterval {
            tlv:id 4;
            type uint8;
            description
                "TLV [93.4.4]: Oob55d2Config.Oob55d2Module.DefaultRangingInterval";
        }

        leaf DefaultRangingSlotConfiguration {
            tlv:id 5;
            type uint16;
            description
                "TLV [93.4.5]: Oob55d2Config.Oob55d2Module.DefaultRangingSlotConfiguration";
        }

        leaf DefaultNonRangingSlotConfiguration {
            tlv:id 6;
            type uint16;
            description
                "TLV [93.4.6]: Oob55d2Config.Oob55d2Module.DefaultNonRangingSlotConfiguration";
        }

        leaf Randomizer {
            tlv:id 7;
            tlv:repr uint8;
            type enumeration {
                enum Polynominal_X6_X_1     { value  0; description ""; }
                enum Polynominal_X6_X5_1    { value  1; description ""; }
            }
            description "TLV [93.4.7]: Oob55d2Config.Oob55d2Module.Randomizer";
        }

        leaf DsPowerAdjust {
            tlv:id 8;
            type int16;
            units "TenthdB";
            description "TLV [93.4.8]: Oob55d2Config.Oob55d2Module.DsPowerAdjust";
        }

        leaf DsPortAssociation {
            tlv:id 9;
            type uint8;
            description
                "TLV [93.4.9]: Oob55d2Config.Oob55d2Module.DsPortAssociation
                 non-defaults: [is_rcp_readonly: True, is_readonly: True]";
        }

        list Oob55d2Demod {
            tlv:id 10;
            key "DemodIndex";
            description "TLV [93.4.10]: Oob55d2Config.Oob55d2Module.Oob55d2Demod";
            uses "p-oob55d2-demod:g-Oob55d2Demod";
        }

        leaf RfMute {
            tlv:id 11;
            type boolean;
            description "TLV [93.4.11]: Oob55d2Config.Oob55d2Module.RfMute";
        }

    }  // g-Oob55d2Module grouping

}
