module us-ofdma-config-query-module {
    yang-version 1;
    /* This file is automatically generated with Falcon V System's script.
       Any change made to this file will be lost. */

    namespace "falconvsystems:r-phy-10:us-ofdma-config-query-module";
    prefix "p-us-ofdma-config-query";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UsOfdmaConfigQuery {
        tlv:id 152;
        description "TLV [152]: UsOfdmaConfigQuery";

        leaf QueryOfdmaRollOffPeriod {
            tlv:id 1;
            type uint16;
            description "TLV [152.1]: UsOfdmaConfigQuery.QueryOfdmaRollOffPeriod";
        }

        leaf QueryOfdmaCyclicPrefix {
            tlv:id 2;
            type uint16;
            description "TLV [152.2]: UsOfdmaConfigQuery.QueryOfdmaCyclicPrefix";
        }

        leaf QueryOfdmaSubcarrierSpacing {
            tlv:id 3;
            type uint8;
            description "TLV [152.3]: UsOfdmaConfigQuery.QueryOfdmaSubcarrierSpacing";
        }

        leaf QueryNumSymbolsPerFrame {
            tlv:id 4;
            type uint8;
            description "TLV [152.4]: UsOfdmaConfigQuery.QueryNumSymbolsPerFrame";
        }

        leaf QueryOfdmaScramblerSeed {
            tlv:id 5;
            type uint32;
            description "TLV [152.5]: UsOfdmaConfigQuery.QueryOfdmaScramblerSeed";
        }

    }  // g-UsOfdmaConfigQuery grouping

}
