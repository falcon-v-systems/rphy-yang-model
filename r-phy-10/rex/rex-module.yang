module rex-module {
    yang-version 1;
    /* This file is automatically generated with Falcon V System's script.
       Any change made to this file will be lost. */

    namespace "falconvsystems:r-phy-10:rex-module";
    prefix "p-rex";

    // --- imports ---------------------------------------

    import core-gcp-connection-response-module {
        prefix "p-core-gcp-connection-response";
        /*  File path: rex/core-gcp-connection-response/core-gcp-connection-response-module.yang
            https://github.com/falcon-v-systems/rphy-yang-model/blob/master/r-phy-10/rex/core-gcp-connection-response/core-gcp-connection-response-module.yang */
    }

    import docs-if-module {
        prefix "p-docs-if";
        /*  File path: rex/docs-if/docs-if-module.yang
            https://github.com/falcon-v-systems/rphy-yang-model/blob/master/r-phy-10/rex/docs-if/docs-if-module.yang */
    }

    import docs-if3-module {
        prefix "p-docs-if3";
        /*  File path: rex/docs-if3/docs-if3-module.yang
            https://github.com/falcon-v-systems/rphy-yang-model/blob/master/r-phy-10/rex/docs-if3/docs-if3-module.yang */
    }

    import docs-if31-module {
        prefix "p-docs-if31";
        /*  File path: rex/docs-if31/docs-if31-module.yang
            https://github.com/falcon-v-systems/rphy-yang-model/blob/master/r-phy-10/rex/docs-if31/docs-if31-module.yang */
    }

    import ds-ofdm-profile-module {
        prefix "p-ds-ofdm-profile";
        /*  File path: rex/ds-ofdm-profile/ds-ofdm-profile-module.yang
            https://github.com/falcon-v-systems/rphy-yang-model/blob/master/r-phy-10/rex/ds-ofdm-profile/ds-ofdm-profile-module.yang */
    }

    import ds-oob55d1-module {
        prefix "p-ds-oob55d1";
        /*  File path: rex/ds-oob55d1/ds-oob55d1-module.yang
            https://github.com/falcon-v-systems/rphy-yang-model/blob/master/r-phy-10/rex/ds-oob55d1/ds-oob55d1-module.yang */
    }

    import enet-port-module {
        prefix "p-enet-port";
        /*  File path: rex/enet-port/enet-port-module.yang
            https://github.com/falcon-v-systems/rphy-yang-model/blob/master/r-phy-10/rex/enet-port/enet-port-module.yang */
    }

    import event-notification-module {
        prefix "p-event-notification";
        /*  File path: rex/event-notification/event-notification-module.yang
            https://github.com/falcon-v-systems/rphy-yang-model/blob/master/r-phy-10/rex/event-notification/event-notification-module.yang */
    }

    import fft-module {
        prefix "p-fft";
        /*  File path: rex/fft/fft-module.yang
            https://github.com/falcon-v-systems/rphy-yang-model/blob/master/r-phy-10/rex/fft/fft-module.yang */
    }

    import gcp-handover-control-module {
        prefix "p-gcp-handover-control";
        /*  File path: rex/gcp-handover-control/gcp-handover-control-module.yang
            https://github.com/falcon-v-systems/rphy-yang-model/blob/master/r-phy-10/rex/gcp-handover-control/gcp-handover-control-module.yang */
    }

    import multi-core-module {
        prefix "p-multi-core";
        /*  File path: rex/multi-core/multi-core-module.yang
            https://github.com/falcon-v-systems/rphy-yang-model/blob/master/r-phy-10/rex/multi-core/multi-core-module.yang */
    }

    import ndf-config-module {
        prefix "p-ndf-config";
        /*  File path: rex/ndf-config/ndf-config-module.yang
            https://github.com/falcon-v-systems/rphy-yang-model/blob/master/r-phy-10/rex/ndf-config/ndf-config-module.yang */
    }

    import ndr-config-module {
        prefix "p-ndr-config";
        /*  File path: rex/ndr-config/ndr-config-module.yang
            https://github.com/falcon-v-systems/rphy-yang-model/blob/master/r-phy-10/rex/ndr-config/ndr-config-module.yang */
    }

    import oob55d2-config-module {
        prefix "p-oob55d2-config";
        /*  File path: rex/oob55d2-config/oob55d2-config-module.yang
            https://github.com/falcon-v-systems/rphy-yang-model/blob/master/r-phy-10/rex/oob55d2-config/oob55d2-config-module.yang */
    }

    import output-buffer-occupancy-history-module {
        prefix "p-output-buffer-occupancy-history";
        /*  File path: rex/output-buffer-occupancy-history/output-buffer-occupancy-history-module.yang
            https://github.com/falcon-v-systems/rphy-yang-model/blob/master/r-phy-10/rex/output-buffer-occupancy-history/output-buffer-occupancy-history-module.yang */
    }

    import output-buffer-threshold-alert-module {
        prefix "p-output-buffer-threshold-alert";
        /*  File path: rex/output-buffer-threshold-alert/output-buffer-threshold-alert-module.yang
            https://github.com/falcon-v-systems/rphy-yang-model/blob/master/r-phy-10/rex/output-buffer-threshold-alert/output-buffer-threshold-alert-module.yang */
    }

    import pnm-us-histogram-module {
        prefix "p-pnm-us-histogram";
        /*  File path: rex/pnm-us-histogram/pnm-us-histogram-module.yang
            https://github.com/falcon-v-systems/rphy-yang-model/blob/master/r-phy-10/rex/pnm-us-histogram/pnm-us-histogram-module.yang */
    }

    import rdti-config-module {
        prefix "p-rdti-config";
        /*  File path: rex/rdti-config/rdti-config-module.yang
            https://github.com/falcon-v-systems/rphy-yang-model/blob/master/r-phy-10/rex/rdti-config/rdti-config-module.yang */
    }

    import rf-channel-module {
        prefix "p-rf-channel";
        /*  File path: rex/rf-channel/rf-channel-module.yang
            https://github.com/falcon-v-systems/rphy-yang-model/blob/master/r-phy-10/rex/rf-channel/rf-channel-module.yang */
    }

    import rf-port-module {
        prefix "p-rf-port";
        /*  File path: rex/rf-port/rf-port-module.yang
            https://github.com/falcon-v-systems/rphy-yang-model/blob/master/r-phy-10/rex/rf-port/rf-port-module.yang */
    }

    import rpd-backup-core-status-table-module {
        prefix "p-rpd-backup-core-status-table";
        /*  File path: rex/rpd-backup-core-status-table/rpd-backup-core-status-table-module.yang
            https://github.com/falcon-v-systems/rphy-yang-model/blob/master/r-phy-10/rex/rpd-backup-core-status-table/rpd-backup-core-status-table-module.yang */
    }

    import rpd-connection-status-module {
        prefix "p-rpd-connection-status";
        /*  File path: rex/rpd-connection-status/rpd-connection-status-module.yang
            https://github.com/falcon-v-systems/rphy-yang-model/blob/master/r-phy-10/rex/rpd-connection-status/rpd-connection-status-module.yang */
    }

    import rpd-ctrl-module {
        prefix "p-rpd-ctrl";
        /*  File path: rex/rpd-ctrl/rpd-ctrl-module.yang
            https://github.com/falcon-v-systems/rphy-yang-model/blob/master/r-phy-10/rex/rpd-ctrl/rpd-ctrl-module.yang */
    }

    import rpd-global-module {
        prefix "p-rpd-global";
        /*  File path: rex/rpd-global/rpd-global-module.yang
            https://github.com/falcon-v-systems/rphy-yang-model/blob/master/r-phy-10/rex/rpd-global/rpd-global-module.yang */
    }

    import rpd-info-module {
        prefix "p-rpd-info";
        /*  File path: rex/rpd-info/rpd-info-module.yang
            https://github.com/falcon-v-systems/rphy-yang-model/blob/master/r-phy-10/rex/rpd-info/rpd-info-module.yang */
    }

    import rpd-redirect-module {
        prefix "p-rpd-redirect";
        /*  File path: rex/rpd-redirect/rpd-redirect-module.yang
            https://github.com/falcon-v-systems/rphy-yang-model/blob/master/r-phy-10/rex/rpd-redirect/rpd-redirect-module.yang */
    }

    import rpd-state-module {
        prefix "p-rpd-state";
        /*  File path: rex/rpd-state/rpd-state-module.yang
            https://github.com/falcon-v-systems/rphy-yang-model/blob/master/r-phy-10/rex/rpd-state/rpd-state-module.yang */
    }

    import sid-qos-module {
        prefix "p-sid-qos";
        /*  File path: rex/sid-qos/sid-qos-module.yang
            https://github.com/falcon-v-systems/rphy-yang-model/blob/master/r-phy-10/rex/sid-qos/sid-qos-module.yang */
    }

    import ssd-module {
        prefix "p-ssd";
        /*  File path: rex/ssd/ssd-module.yang
            https://github.com/falcon-v-systems/rphy-yang-model/blob/master/r-phy-10/rex/ssd/ssd-module.yang */
    }

    import static-pw-config-module {
        prefix "p-static-pw-config";
        /*  File path: rex/static-pw-config/static-pw-config-module.yang
            https://github.com/falcon-v-systems/rphy-yang-model/blob/master/r-phy-10/rex/static-pw-config/static-pw-config-module.yang */
    }

    import static-pw-status-module {
        prefix "p-static-pw-status";
        /*  File path: rex/static-pw-status/static-pw-status-module.yang
            https://github.com/falcon-v-systems/rphy-yang-model/blob/master/r-phy-10/rex/static-pw-status/static-pw-status-module.yang */
    }

    import tlv-extension {
        prefix "tlv";
        /*  Falcon's Yang extension for TLV attributes. */
    }

    import us-ofdma-config-query-module {
        prefix "p-us-ofdma-config-query";
        /*  File path: rex/us-ofdma-config-query/us-ofdma-config-query-module.yang
            https://github.com/falcon-v-systems/rphy-yang-model/blob/master/r-phy-10/rex/us-ofdma-config-query/us-ofdma-config-query-module.yang */
    }

    import us-ofdma-config-response-module {
        prefix "p-us-ofdma-config-response";
        /*  File path: rex/us-ofdma-config-response/us-ofdma-config-response-module.yang
            https://github.com/falcon-v-systems/rphy-yang-model/blob/master/r-phy-10/rex/us-ofdma-config-response/us-ofdma-config-response-module.yang */
    }

    import us-ofdma-data-iuc-module {
        prefix "p-us-ofdma-data-iuc";
        /*  File path: rex/us-ofdma-data-iuc/us-ofdma-data-iuc-module.yang
            https://github.com/falcon-v-systems/rphy-yang-model/blob/master/r-phy-10/rex/us-ofdma-data-iuc/us-ofdma-data-iuc-module.yang */
    }

    import us-ofdma-fine-ranging-iuc-module {
        prefix "p-us-ofdma-fine-ranging-iuc";
        /*  File path: rex/us-ofdma-fine-ranging-iuc/us-ofdma-fine-ranging-iuc-module.yang
            https://github.com/falcon-v-systems/rphy-yang-model/blob/master/r-phy-10/rex/us-ofdma-fine-ranging-iuc/us-ofdma-fine-ranging-iuc-module.yang */
    }

    import us-ofdma-initial-ranging-iuc-module {
        prefix "p-us-ofdma-initial-ranging-iuc";
        /*  File path: rex/us-ofdma-initial-ranging-iuc/us-ofdma-initial-ranging-iuc-module.yang
            https://github.com/falcon-v-systems/rphy-yang-model/blob/master/r-phy-10/rex/us-ofdma-initial-ranging-iuc/us-ofdma-initial-ranging-iuc-module.yang */
    }

    import us-ofdma-subcarrier-cfg-module {
        prefix "p-us-ofdma-subcarrier-cfg";
        /*  File path: rex/us-ofdma-subcarrier-cfg/us-ofdma-subcarrier-cfg-module.yang
            https://github.com/falcon-v-systems/rphy-yang-model/blob/master/r-phy-10/rex/us-ofdma-subcarrier-cfg/us-ofdma-subcarrier-cfg-module.yang */
    }

    import us-oob55d1-module {
        prefix "p-us-oob55d1";
        /*  File path: rex/us-oob55d1/us-oob55d1-module.yang
            https://github.com/falcon-v-systems/rphy-yang-model/blob/master/r-phy-10/rex/us-oob55d1/us-oob55d1-module.yang */
    }

    import us-sc-qam-profile-query-module {
        prefix "p-us-sc-qam-profile-query";
        /*  File path: rex/us-sc-qam-profile-query/us-sc-qam-profile-query-module.yang
            https://github.com/falcon-v-systems/rphy-yang-model/blob/master/r-phy-10/rex/us-sc-qam-profile-query/us-sc-qam-profile-query-module.yang */
    }

    import us-sc-qam-profile-response-module {
        prefix "p-us-sc-qam-profile-response";
        /*  File path: rex/us-sc-qam-profile-response/us-sc-qam-profile-response-module.yang
            https://github.com/falcon-v-systems/rphy-yang-model/blob/master/r-phy-10/rex/us-sc-qam-profile-response/us-sc-qam-profile-response-module.yang */
    }

    import us-spectrum-capture-module {
        prefix "p-us-spectrum-capture";
        /*  File path: rex/us-spectrum-capture/us-spectrum-capture-module.yang
            https://github.com/falcon-v-systems/rphy-yang-model/blob/master/r-phy-10/rex/us-spectrum-capture/us-spectrum-capture-module.yang */
    }

    import vendor-specific-extension-module {
        prefix "p-vendor-specific-extension";
        /*  File path: rex/vendor-specific-extension/vendor-specific-extension-module.yang
            https://github.com/falcon-v-systems/rphy-yang-model/blob/master/r-phy-10/rex/vendor-specific-extension/vendor-specific-extension-module.yang */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-REX {
        tlv:id 2;
        description "TLV [2]: REX";

        list Sequence {
            tlv:id 9;
            key "SequenceNumber";
            description
                "TLV [9]: Sequence
                 No external definition.";

            leaf SequenceNumber {
                tlv:id 10;
                type uint16;
                description "TLV [10]: SequenceNumber";
            }

            leaf Operation {
                tlv:id 11;
                tlv:repr uint8;
                type enumeration {
                    enum Read                   { value  1; description ""; }
                    enum Write                  { value  2; description ""; }
                    enum Delete                 { value  3; description ""; }
                    enum ReadResponse           { value  4; description ""; }
                    enum WriteResponse          { value  5; description ""; }
                    enum DeleteResponse         { value  6; description ""; }
                    enum AllocateWrite          { value  7; description ""; }
                    enum AllocateWriteResponse  { value  8; description ""; }
                }
                description "TLV [11]: Operation";
            }

            leaf ResponseCode {
                tlv:id 19;
                tlv:repr uint8;
                type enumeration {
                    enum NoError                { value  0; description ""; }
                    enum GeneralError           { value  1; description ""; }
                    enum ResponseTooBig         { value  2; description ""; }
                    enum AttributeNotFound      { value  3; description ""; }
                    enum BadIndex               { value  4; description ""; }
                    enum WriteToReadOnly        { value  5; description ""; }
                    enum InconsistentValue      { value  6; description ""; }
                    enum WrongLength            { value  7; description ""; }
                    enum WrongValue             { value  8; description ""; }
                    enum ResourceUnavailable    { value  9; description ""; }
                    enum AuthorizationFailure   { value 10; description ""; }
                    enum AttributeMissing       { value 11; description ""; }
                    enum AllocationFailure      { value 12; description ""; }
                    enum AllocationNoOwner      { value 13; description ""; }
                    enum ErrorProcessingUCD     { value 14; description ""; }
                    enum ErrorProcessingOCD     { value 15; description ""; }
                    enum ErrorProcessingDPD     { value 16; description ""; }
                }
                description "TLV [19]: ResponseCode";
            }

            leaf ErrorMessage {
                tlv:id 20;
                type string;
                description "TLV [20]: ErrorMessage";
            }

            leaf ReadCount {
                tlv:id 26;
                type uint16;
                description "TLV [26]: ReadCount";
            }

            choice rex-topic {
                case EnetPortIndex {
                    leaf EnetPortIndex {
                        tlv:id 14;
                        type uint8;
                        description "TLV [14]: EnetPortIndex";
                    }
                }

                case RpdGlobal {
                    container RpdGlobal {
                        tlv:id 15;
                        description "TLV [15]: RpdGlobal";
                        uses "p-rpd-global:g-RpdGlobal";
                    }
                }

                case RfChannel {
                    container RfChannel {
                        tlv:id 16;
                        description "TLV [16]: RfChannel";
                        uses "p-rf-channel:g-RfChannel";
                    }
                }

                case RfPort {
                    container RfPort {
                        tlv:id 17;
                        description "TLV [17]: RfPort";
                        uses "p-rf-port:g-RfPort";
                    }
                }

                case EnetPort {
                    container EnetPort {
                        tlv:id 18;
                        description "TLV [18]: EnetPort";
                        uses "p-enet-port:g-EnetPort";
                    }
                }

                case VendorSpecificExtension {
                    container VendorSpecificExtension {
                        tlv:id 21;
                        description "TLV [21]: VendorSpecificExtension";
                        uses "p-vendor-specific-extension:g-VendorSpecificExtension";
                    }
                }

                case DocsisTimestamp32 {
                    leaf DocsisTimestamp32 {
                        tlv:id 23;
                        type uint32;
                        description "TLV [23]: DocsisTimestamp32";
                    }
                }

                case DocsisTimestamp64 {
                    leaf DocsisTimestamp64 {
                        tlv:id 24;
                        type uint64;
                        description "TLV [24]: DocsisTimestamp64";
                    }
                }

                case RpdRedirect {
                    container RpdRedirect {
                        tlv:id 25;
                        description "TLV [25]: RpdRedirect";
                        uses "p-rpd-redirect:g-RpdRedirect";
                    }
                }

                case RpdCtrl {
                    container RpdCtrl {
                        tlv:id 40;
                        description "TLV [40]: RpdCtrl";
                        uses "p-rpd-ctrl:g-RpdCtrl";
                    }
                }

                case UsSpectrumCapture {
                    container UsSpectrumCapture {
                        tlv:id 41;
                        description "TLV [41]: UsSpectrumCapture";
                        uses "p-us-spectrum-capture:g-UsSpectrumCapture";
                    }
                }

                case RpdPtpClockStatus {
                    leaf RpdPtpClockStatus {
                        tlv:id 51;
                        type uint8;
                        description
                            "TLV [51]: RpdPtpClockStatus
                             non-defaults: [is_readonly: True]";
                    }
                }

                case RpdConfigurationDone {
                    leaf RpdConfigurationDone {
                        tlv:id 52;
                        type uint8;
                        description
                            "TLV [52]: RpdConfigurationDone
                             non-defaults: [is_readonly: True]";
                    }
                }

                case StaticPwConfig {
                    container StaticPwConfig {
                        tlv:id 58;
                        description "TLV [58]: StaticPwConfig";
                        uses "p-static-pw-config:g-StaticPwConfig";
                    }
                }

                case StaticPwStatus {
                    container StaticPwStatus {
                        tlv:id 59;
                        description "TLV [59]: StaticPwStatus";
                        uses "p-static-pw-status:g-StaticPwStatus";
                    }
                }

                case DsOfdmProfile {
                    list DsOfdmProfile {
                        tlv:id 64;
                        key "ProfileId";
                        description "TLV [64]: DsOfdmProfile";
                        uses "p-ds-ofdm-profile:g-DsOfdmProfile";
                    }
                }

                case UsOfdmaInitialRangingIuc {
                    container UsOfdmaInitialRangingIuc {
                        tlv:id 67;
                        description "TLV [67]: UsOfdmaInitialRangingIuc";
                        uses "p-us-ofdma-initial-ranging-iuc:g-UsOfdmaInitialRangingIuc";
                    }
                }

                case UsOfdmaFineRangingIuc {
                    container UsOfdmaFineRangingIuc {
                        tlv:id 68;
                        description "TLV [68]: UsOfdmaFineRangingIuc";
                        uses "p-us-ofdma-fine-ranging-iuc:g-UsOfdmaFineRangingIuc";
                    }
                }

                case UsOfdmaDataIuc {
                    list UsOfdmaDataIuc {
                        tlv:id 69;
                        key "DataIuc";
                        description "TLV [69]: UsOfdmaDataIuc";
                        uses "p-us-ofdma-data-iuc:g-UsOfdmaDataIuc";
                    }
                }

                case UsOfdmaSubcarrierCfg {
                    list UsOfdmaSubcarrierCfg {
                        tlv:id 70;
                        key "StartingSubcarrierId";
                        description "TLV [70]: UsOfdmaSubcarrierCfg";
                        uses "p-us-ofdma-subcarrier-cfg:g-UsOfdmaSubcarrierCfg";
                    }
                }

                case OutputBufferOccupancyHistory {
                    container OutputBufferOccupancyHistory {
                        tlv:id 83;
                        description "TLV [83]: OutputBufferOccupancyHistory";
                        uses "p-output-buffer-occupancy-history:g-OutputBufferOccupancyHistory";
                    }
                }

                case OutputBufferThresholdAlert {
                    container OutputBufferThresholdAlert {
                        tlv:id 84;
                        description "TLV [84]: OutputBufferThresholdAlert";
                        uses "p-output-buffer-threshold-alert:g-OutputBufferThresholdAlert";
                    }
                }

                case EventNotification {
                    container EventNotification {
                        tlv:id 85;
                        description "TLV [85]: EventNotification";
                        uses "p-event-notification:g-EventNotification";
                    }
                }

                case RpdState {
                    container RpdState {
                        tlv:id 87;
                        description
                            "TLV [87]: RpdState
                             non-defaults: [is_rcp_readonly: True, is_readonly: True]";
                        uses "p-rpd-state:g-RpdState";
                    }
                }

                case MultiCore {
                    container MultiCore {
                        tlv:id 88;
                        description
                            "TLV [88]: MultiCore
                             non-defaults: [is_rcp_readonly: True, is_readonly: True]";
                        uses "p-multi-core:g-MultiCore";
                    }
                }

                case Ssd {
                    container Ssd {
                        tlv:id 90;
                        description "TLV [90]: Ssd";
                        uses "p-ssd:g-Ssd";
                    }
                }

                case DsOob55d1 {
                    container DsOob55d1 {
                        tlv:id 91;
                        description "TLV [91]: DsOob55d1";
                        uses "p-ds-oob55d1:g-DsOob55d1";
                    }
                }

                case UsOob55d1 {
                    list UsOob55d1 {
                        tlv:id 92;
                        key "Index";
                        description "TLV [92]: UsOob55d1";
                        uses "p-us-oob55d1:g-UsOob55d1";
                    }
                }

                case Oob55d2Config {
                    container Oob55d2Config {
                        tlv:id 93;
                        description "TLV [93]: Oob55d2Config";
                        uses "p-oob55d2-config:g-Oob55d2Config";
                    }
                }

                case NdfConfig {
                    list NdfConfig {
                        tlv:id 94;
                        key "Index";
                        description "TLV [94]: NdfConfig";
                        uses "p-ndf-config:g-NdfConfig";
                    }
                }

                case NdrConfig {
                    list NdrConfig {
                        tlv:id 95;
                        key "Index";
                        description "TLV [95]: NdrConfig";
                        uses "p-ndr-config:g-NdrConfig";
                    }
                }

                case SidQos {
                    list SidQos {
                        tlv:id 96;
                        key "StartSid";
                        description "TLV [96]: SidQos";
                        uses "p-sid-qos:g-SidQos";
                    }
                }

                case RdtiConfig {
                    container RdtiConfig {
                        tlv:id 97;
                        description "TLV [97]: RdtiConfig";
                        uses "p-rdti-config:g-RdtiConfig";
                    }
                }

                case Fft {
                    container Fft {
                        tlv:id 99;
                        description
                            "TLV [99]: Fft
                             non-defaults: [is_readonly: True]";
                        uses "p-fft:g-Fft";
                    }
                }

                case RpdInfo {
                    container RpdInfo {
                        tlv:id 100;
                        description "TLV [100]: RpdInfo";
                        uses "p-rpd-info:g-RpdInfo";
                    }
                }

                case DocsIf31 {
                    container DocsIf31 {
                        tlv:id 101;
                        description
                            "TLV [101]: DocsIf31
                             non-defaults: [is_rcp_readonly: True, is_readonly: True]";
                        uses "p-docs-if31:g-DocsIf31";
                    }
                }

                case DocsIf3 {
                    container DocsIf3 {
                        tlv:id 102;
                        description
                            "TLV [102]: DocsIf3
                             non-defaults: [is_rcp_readonly: True, is_readonly: True]";
                        uses "p-docs-if3:g-DocsIf3";
                    }
                }

                case DocsIf {
                    container DocsIf {
                        tlv:id 103;
                        description
                            "TLV [103]: DocsIf
                             non-defaults: [is_rcp_readonly: True, is_readonly: True]";
                        uses "p-docs-if:g-DocsIf";
                    }
                }

                case RpdConnectionStatus {
                    list RpdConnectionStatus {
                        tlv:id 105;
                        key "Index";
                        description "TLV [105]: RpdConnectionStatus";
                        uses "p-rpd-connection-status:g-RpdConnectionStatus";
                    }
                }

                case CoreGcpConnectionResponse {
                    container CoreGcpConnectionResponse {
                        tlv:id 106;
                        description "TLV [106]: CoreGcpConnectionResponse";
                        uses "p-core-gcp-connection-response:g-CoreGcpConnectionResponse";
                    }
                }

                case RpdBackupCoreStatusTable {
                    list RpdBackupCoreStatusTable {
                        tlv:id 107;
                        key "Index";
                        description "TLV [107]: RpdBackupCoreStatusTable";
                        uses "p-rpd-backup-core-status-table:g-RpdBackupCoreStatusTable";
                    }
                }

                case GcpHandoverControl {
                    container GcpHandoverControl {
                        tlv:id 109;
                        description "TLV [109]: GcpHandoverControl";
                        uses "p-gcp-handover-control:g-GcpHandoverControl";
                    }
                }

                case PnmUsHistogram {
                    container PnmUsHistogram {
                        tlv:id 131;
                        description "TLV [131]: PnmUsHistogram";
                        uses "p-pnm-us-histogram:g-PnmUsHistogram";
                    }
                }

                case UsScQamProfileQuery {
                    container UsScQamProfileQuery {
                        tlv:id 150;
                        description "TLV [150]: UsScQamProfileQuery";
                        uses "p-us-sc-qam-profile-query:g-UsScQamProfileQuery";
                    }
                }

                case UsScQamProfileResponse {
                    container UsScQamProfileResponse {
                        tlv:id 151;
                        description
                            "TLV [151]: UsScQamProfileResponse
                             non-defaults: [is_rcp_readonly: True]";
                        uses "p-us-sc-qam-profile-response:g-UsScQamProfileResponse";
                    }
                }

                case UsOfdmaConfigQuery {
                    container UsOfdmaConfigQuery {
                        tlv:id 152;
                        description "TLV [152]: UsOfdmaConfigQuery";
                        uses "p-us-ofdma-config-query:g-UsOfdmaConfigQuery";
                    }
                }

                case UsOfdmaConfigResponse {
                    container UsOfdmaConfigResponse {
                        tlv:id 153;
                        description
                            "TLV [153]: UsOfdmaConfigResponse
                             non-defaults: [is_rcp_readonly: True]";
                        uses "p-us-ofdma-config-response:g-UsOfdmaConfigResponse";
                    }
                }

                description 
                    "The choice statement defines a set of alternatives,
                     only one of which may exist at any one time.";
            }
        }  // Sequence list

    }  // g-REX grouping

}
