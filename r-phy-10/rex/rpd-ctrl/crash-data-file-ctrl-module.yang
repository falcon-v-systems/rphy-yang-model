module crash-data-file-ctrl-module {
    yang-version 1;
    /* This file is automatically generated with Falcon V System's script.
       Any change made to this file will be lost. */

    namespace "falconvsystems:r-phy-10:crash-data-file-ctrl-module";
    prefix "p-crash-data-file-ctrl";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-CrashDataFileCtrl {
        tlv:id 3;
        description "TLV [40.3]: RpdCtrl.CrashDataFileCtrl";

        leaf Index {
            tlv:id 1;
            type uint8;
            description "TLV [40.3.1]: RpdCtrl.CrashDataFileCtrl.Index";
        }

        leaf FileControl {
            tlv:id 2;
            tlv:repr uint8;
            type enumeration {
                enum other              { value  1; description ""; }
                enum upload             { value  2; description ""; }
                enum cancelUpload       { value  3; description ""; }
                enum deleteFile         { value  4; description ""; }
                enum uploadAndDelete    { value  5; description ""; }
            }
            description "TLV [40.3.2]: RpdCtrl.CrashDataFileCtrl.FileControl";
        }

    }  // g-CrashDataFileCtrl grouping

}
