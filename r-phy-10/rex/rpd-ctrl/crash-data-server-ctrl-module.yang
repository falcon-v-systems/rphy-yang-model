module crash-data-server-ctrl-module {
    yang-version 1;
    /* This file is automatically generated with Falcon V System's script.
       Any change made to this file will be lost. */

    namespace "falconvsystems:r-phy-10:crash-data-server-ctrl-module";
    prefix "p-crash-data-server-ctrl";

    // --- imports ---------------------------------------

    import ietf-inet-types {
        prefix "inet";
        /*  External YANG module. */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-CrashDataServerCtrl {
        tlv:id 4;
        description "TLV [40.4]: RpdCtrl.CrashDataServerCtrl";

        leaf DestIpAddress {
            tlv:id 1;
            type inet:ip-address;
            description "TLV [40.4.1]: RpdCtrl.CrashDataServerCtrl.DestIpAddress";
        }

        leaf DestPath {
            tlv:id 2;
            type string;
            description "TLV [40.4.2]: RpdCtrl.CrashDataServerCtrl.DestPath";
        }

        leaf Protocol {
            tlv:id 3;
            tlv:repr uint8;
            type enumeration {
                enum tftp   { value  2; description ""; }
                enum http   { value  3; description ""; }
            }
            description "TLV [40.4.3]: RpdCtrl.CrashDataServerCtrl.Protocol";
        }

    }  // g-CrashDataServerCtrl grouping

}
