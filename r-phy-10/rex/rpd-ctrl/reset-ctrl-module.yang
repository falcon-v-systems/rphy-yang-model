module reset-ctrl-module {
    yang-version 1;
    /* This file is automatically generated with Falcon V System's script.
       Any change made to this file will be lost. */

    namespace "falconvsystems:r-phy-10:reset-ctrl-module";
    prefix "p-reset-ctrl";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-ResetCtrl {
        tlv:id 1;
        description "TLV [40.1]: RpdCtrl.ResetCtrl";

        leaf Reset {
            tlv:id 1;
            tlv:repr uint8;
            type enumeration {
                enum softReset      { value  1; description ""; }
                enum hardReset      { value  2; description ""; }
                enum nvReset        { value  3; description ""; }
                enum factoryReset   { value  4; description ""; }
            }
            description "TLV [40.1.1]: RpdCtrl.ResetCtrl.Reset";
        }

    }  // g-ResetCtrl grouping

}
