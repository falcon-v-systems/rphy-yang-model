module reboot-disable-ctrl-module {
    yang-version 1;
    /* This file is automatically generated with Falcon V System's script.
       Any change made to this file will be lost. */

    namespace "falconvsystems:r-phy-10:reboot-disable-ctrl-module";
    prefix "p-reboot-disable-ctrl";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-RebootDisableCtrl {
        tlv:id 5;
        description "TLV [40.5]: RpdCtrl.RebootDisableCtrl";

        leaf RebootDisable {
            tlv:id 1;
            type boolean;
            description "TLV [40.5.1]: RpdCtrl.RebootDisableCtrl.RebootDisable";
        }

        leaf DisableTimeout {
            tlv:id 2;
            type uint32;
            units "seconds";
            description "TLV [40.5.2]: RpdCtrl.RebootDisableCtrl.DisableTimeout";
        }

    }  // g-RebootDisableCtrl grouping

}
