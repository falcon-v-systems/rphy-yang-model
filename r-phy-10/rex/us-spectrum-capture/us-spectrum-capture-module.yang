module us-spectrum-capture-module {
    yang-version 1;
    /* This file is automatically generated with Falcon V System's script.
       Any change made to this file will be lost. */

    namespace "falconvsystems:r-phy-10:us-spectrum-capture-module";
    prefix "p-us-spectrum-capture";

    // --- imports ---------------------------------------

    import tlv-extension {
        prefix "tlv";
        /*  Falcon's Yang extension for TLV attributes. */
    }

    import usc-config-module {
        prefix "p-usc-config";
        /*  File path: rex/us-spectrum-capture/usc-config-module.yang
            https://github.com/falcon-v-systems/rphy-yang-model/blob/master/r-phy-10/rex/us-spectrum-capture/usc-config-module.yang */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UsSpectrumCapture {
        tlv:id 41;
        description "TLV [41]: UsSpectrumCapture";

        leaf UscSacIndex {
            tlv:id 1;
            type uint8;
            description "TLV [41.1]: UsSpectrumCapture.UscSacIndex";
        }

        leaf UscCommand {
            tlv:id 2;
            tlv:repr uint8;
            type enumeration {
                enum StartCapture   { value  1; description ""; }
                enum StopCapture    { value  2; description ""; }
            }
            description "TLV [41.2]: UsSpectrumCapture.UscCommand";
        }

        leaf UscStatus {
            tlv:id 3;
            tlv:repr uint8;
            type enumeration {
                enum other                  { value  1; description ""; }
                enum inactive               { value  2; description ""; }
                enum busy                   { value  3; description ""; }
                enum sampleReady            { value  4; description ""; }
                enum error                  { value  5; description ""; }
                enum resourceUnavailable    { value  6; description ""; }
                enum sampleTruncated        { value  7; description ""; }
            }
            description "TLV [41.3]: UsSpectrumCapture.UscStatus";
        }

        container UscConfig {
            tlv:id 4;
            description "TLV [41.4]: UsSpectrumCapture.UscConfig";
            uses "p-usc-config:g-UscConfig";
        }

    }  // g-UsSpectrumCapture grouping

}
