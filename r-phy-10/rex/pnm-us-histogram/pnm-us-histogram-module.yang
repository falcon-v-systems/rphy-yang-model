module pnm-us-histogram-module {
    yang-version 1;
    /* This file is automatically generated with Falcon V System's script.
       Any change made to this file will be lost. */

    namespace "falconvsystems:r-phy-10:pnm-us-histogram-module";
    prefix "p-pnm-us-histogram";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-PnmUsHistogram {
        tlv:id 131;
        description "TLV [131]: PnmUsHistogram";

        leaf UsHsgRpdStatus {
            tlv:id 1;
            tlv:repr uint8;
            type enumeration {
                enum Idle           { value  1; description ""; }
                enum InProgress     { value  2; description ""; }
                enum ResultsReady   { value  3; description ""; }
                enum Error          { value  4; description ""; }
            }
            description "TLV [131.1]: PnmUsHistogram.UsHsgRpdStatus";
        }

        leaf UsHsgCommand {
            tlv:id 2;
            tlv:repr uint8;
            type enumeration {
                enum StartTest  { value  1; description ""; }
                enum StopTest   { value  2; description ""; }
                enum Reset      { value  3; description ""; }
                enum Abort      { value  4; description ""; }
            }
            description "TLV [131.2]: PnmUsHistogram.UsHsgCommand";
        }

        leaf UsHsgRfPortId {
            tlv:id 3;
            type uint16;
            description "TLV [131.3]: PnmUsHistogram.UsHsgRfPortId";
        }

        leaf UsHsgTimeout {
            tlv:id 4;
            type uint16;
            description "TLV [131.4]: PnmUsHistogram.UsHsgTimeout";
        }

        leaf UsHsgEvenSymmetry {
            tlv:id 5;
            type boolean;
            description "TLV [131.5]: PnmUsHistogram.UsHsgEvenSymmetry";
        }

        leaf UsHsgStartTime {
            tlv:id 6;
            type uint64;
            description "TLV [131.6]: PnmUsHistogram.UsHsgStartTime";
        }

        leaf UsHsgEndTime {
            tlv:id 7;
            type uint64;
            description "TLV [131.7]: PnmUsHistogram.UsHsgEndTime";
        }

        leaf UsHsgDwellCounts {
            tlv:id 8;
            type binary;
            description "TLV [131.8]: PnmUsHistogram.UsHsgDwellCounts";
        }

        leaf UsHsgHitCounts {
            tlv:id 9;
            type binary;
            description "TLV [131.9]: PnmUsHistogram.UsHsgHitCounts";
        }

    }  // g-PnmUsHistogram grouping

}
