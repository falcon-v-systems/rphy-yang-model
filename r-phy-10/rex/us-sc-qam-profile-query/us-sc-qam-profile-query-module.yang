module us-sc-qam-profile-query-module {
    yang-version 1;
    /* This file is automatically generated with Falcon V System's script.
       Any change made to this file will be lost. */

    namespace "falconvsystems:r-phy-10:us-sc-qam-profile-query-module";
    prefix "p-us-sc-qam-profile-query";

    // --- imports ---------------------------------------

    import query-iuc-code-module {
        prefix "p-query-iuc-code";
        /*  File path: rex/us-sc-qam-profile-query/query-iuc-code-module.yang
            https://github.com/falcon-v-systems/rphy-yang-model/blob/master/r-phy-10/rex/us-sc-qam-profile-query/query-iuc-code-module.yang */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UsScQamProfileQuery {
        tlv:id 150;
        description "TLV [150]: UsScQamProfileQuery";

        leaf QueryScQamChannelType {
            tlv:id 1;
            type uint8;
            description "TLV [150.1]: UsScQamProfileQuery.QueryScQamChannelType";
        }

        leaf QueryScQamWidth {
            tlv:id 2;
            type uint32;
            description "TLV [150.2]: UsScQamProfileQuery.QueryScQamWidth";
        }

        container QueryIucCode {
            tlv:id 3;
            description "TLV [150.3]: UsScQamProfileQuery.QueryIucCode";
            uses "p-query-iuc-code:g-QueryIucCode";
        }

    }  // g-UsScQamProfileQuery grouping

}
