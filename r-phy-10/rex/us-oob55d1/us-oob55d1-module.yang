module us-oob55d1-module {
    yang-version 1;
    /* This file is automatically generated with Falcon V System's script.
       Any change made to this file will be lost. */

    namespace "falconvsystems:r-phy-10:us-oob55d1-module";
    prefix "p-us-oob55d1";

    // --- imports ---------------------------------------

    import ietf-yang-types {
        prefix "yang";
        /*  External YANG module. */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UsOob55d1 {
        tlv:id 92;
        description "TLV [92]: UsOob55d1";

        leaf Index {
            // no tlv:id given
            type uint16;
            description
                "TLV [92.X]: UsOob55d1.Index
                 non-defaults: [is_key: True]";
        }

        leaf AdminState {
            tlv:id 1;
            tlv:repr uint8;
            type enumeration {
                enum other      { value  1; description ""; }
                enum up         { value  2; description ""; }
                enum down       { value  3; description ""; }
                enum testing    { value  4; description ""; }
            }
            description "TLV [92.1]: UsOob55d1.AdminState";
        }

        leaf CcapCoreOwner {
            tlv:id 2;
            type yang:mac-address;
            description "TLV [92.2]: UsOob55d1.CcapCoreOwner";
        }

        leaf Frequency {
            tlv:id 3;
            type uint32;
            units "Hz";
            description "TLV [92.3]: UsOob55d1.Frequency";
        }

        leaf VarpdDeviceId {
            tlv:id 4;
            type uint32;
            description "TLV [92.4]: UsOob55d1.VarpdDeviceId";
        }

        leaf VarpdRfPortId {
            tlv:id 5;
            type uint8;
            description "TLV [92.5]: UsOob55d1.VarpdRfPortId";
        }

        leaf VarpdDemodId {
            tlv:id 6;
            type uint8;
            description "TLV [92.6]: UsOob55d1.VarpdDemodId";
        }

        leaf TargetRxPowerAdjust {
            tlv:id 7;
            type int16;
            units "TenthDb";
            description "TLV [92.7]: UsOob55d1.TargetRxPowerAdjust";
        }

    }  // g-UsOob55d1 grouping

}
