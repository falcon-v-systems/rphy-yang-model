module common-static-pw-status-module {
    yang-version 1;
    /* This file is automatically generated with Falcon V System's script.
       Any change made to this file will be lost. */

    namespace "falconvsystems:r-phy-10:common-static-pw-status-module";
    prefix "p-common-static-pw-status";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-CommonStaticPwStatus {
        tlv:id 1;
        description "TLV [59.1]: StaticPwStatus.CommonStaticPwStatus";

        leaf Direction {
            tlv:id 1;
            tlv:repr uint8;
            type enumeration {
                enum ForwardDirPseudowire   { value  0; description ""; }
                enum ReturnDirPseudowire    { value  1; description ""; }
            }
            description "TLV [59.1.1]: StaticPwStatus.CommonStaticPwStatus.Direction";
        }

        leaf Index {
            tlv:id 2;
            type uint16;
            description "TLV [59.1.2]: StaticPwStatus.CommonStaticPwStatus.Index";
        }

        leaf RpdCircuitStatus {
            tlv:id 3;
            type uint16;
            description
                "TLV [59.1.3]: StaticPwStatus.CommonStaticPwStatus.RpdCircuitStatus
                 non-defaults: [is_rcp_readonly: True, is_readonly: True]";
        }

    }  // g-CommonStaticPwStatus grouping

}
