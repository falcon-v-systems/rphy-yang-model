module rpd-global-module {
    yang-version 1;
    /* This file is automatically generated with Falcon V System's script.
       Any change made to this file will be lost. */

    namespace "falconvsystems:r-phy-10:rpd-global-module";
    prefix "p-rpd-global";

    // --- imports ---------------------------------------

    import ev-cfg-module {
        prefix "p-ev-cfg";
        /*  File path: rex/rpd-global/ev-cfg/ev-cfg-module.yang
            https://github.com/falcon-v-systems/rphy-yang-model/blob/master/r-phy-10/rex/rpd-global/ev-cfg/ev-cfg-module.yang */
    }

    import gcp-conn-verification-module {
        prefix "p-gcp-conn-verification";
        /*  File path: rex/rpd-global/gcp-conn-verification-module.yang
            https://github.com/falcon-v-systems/rphy-yang-model/blob/master/r-phy-10/rex/rpd-global/gcp-conn-verification-module.yang */
    }

    import ip-config-module {
        prefix "p-ip-config";
        /*  File path: rex/rpd-global/ip-config-module.yang
            https://github.com/falcon-v-systems/rphy-yang-model/blob/master/r-phy-10/rex/rpd-global/ip-config-module.yang */
    }

    import tlv-extension {
        prefix "tlv";
        /*  Falcon's Yang extension for TLV attributes. */
    }

    import uepi-control-module {
        prefix "p-uepi-control";
        /*  File path: rex/rpd-global/uepi-control-module.yang
            https://github.com/falcon-v-systems/rphy-yang-model/blob/master/r-phy-10/rex/rpd-global/uepi-control-module.yang */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-RpdGlobal {
        tlv:id 15;
        description "TLV [15]: RpdGlobal";

        container EvCfg {
            tlv:id 1;
            description "TLV [15.1]: RpdGlobal.EvCfg";
            uses "p-ev-cfg:g-EvCfg";
        }

        container GcpConnVerification {
            tlv:id 2;
            description "TLV [15.2]: RpdGlobal.GcpConnVerification";
            uses "p-gcp-conn-verification:g-GcpConnVerification";
        }

        container IpConfig {
            tlv:id 3;
            description "TLV [15.3]: RpdGlobal.IpConfig";
            uses "p-ip-config:g-IpConfig";
        }

        container UepiControl {
            tlv:id 4;
            description "TLV [15.4]: RpdGlobal.UepiControl";
            uses "p-uepi-control:g-UepiControl";
        }

        leaf GcpDscp {
            tlv:id 5;
            type uint8;
            description "TLV [15.5]: RpdGlobal.GcpDscp";
        }

    }  // g-RpdGlobal grouping

}
