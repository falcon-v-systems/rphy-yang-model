module ev-cfg-module {
    yang-version 1;
    /* This file is automatically generated with Falcon V System's script.
       Any change made to this file will be lost. */

    namespace "falconvsystems:r-phy-10:ev-cfg-module";
    prefix "p-ev-cfg";

    // --- imports ---------------------------------------

    import ev-control-module {
        prefix "p-ev-control";
        /*  File path: rex/rpd-global/ev-cfg/ev-control-module.yang
            https://github.com/falcon-v-systems/rphy-yang-model/blob/master/r-phy-10/rex/rpd-global/ev-cfg/ev-control-module.yang */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-EvCfg {
        tlv:id 1;
        description "TLV [15.1]: RpdGlobal.EvCfg";

        list EvControl {
            tlv:id 1;
            key "EvPriority";
            description "TLV [15.1.1]: RpdGlobal.EvCfg.EvControl";
            uses "p-ev-control:g-EvControl";
        }

        leaf EvThrottleAdminStatus {
            tlv:id 2;
            tlv:repr uint8;
            type enumeration {
                enum unconstrained          { value  1; description ""; }
                enum maintainBelowThreshold { value  2; description ""; }
                enum stopAtThreshold        { value  3; description ""; }
                enum inhibited              { value  4; description ""; }
            }
            description "TLV [15.1.2]: RpdGlobal.EvCfg.EvThrottleAdminStatus";
        }

        leaf EvThrottleThreshold {
            tlv:id 3;
            type uint32;
            description "TLV [15.1.3]: RpdGlobal.EvCfg.EvThrottleThreshold";
        }

        leaf EvThrottleInterval {
            tlv:id 4;
            type uint32;
            units "Seconds";
            description "TLV [15.1.4]: RpdGlobal.EvCfg.EvThrottleInterval";
        }

        leaf NotifyEnable {
            tlv:id 5;
            type boolean;
            description "TLV [15.1.5]: RpdGlobal.EvCfg.NotifyEnable";
        }

    }  // g-EvCfg grouping

}
