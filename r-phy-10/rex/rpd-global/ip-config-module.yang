module ip-config-module {
    yang-version 1;
    /* This file is automatically generated with Falcon V System's script.
       Any change made to this file will be lost. */

    namespace "falconvsystems:r-phy-10:ip-config-module";
    prefix "p-ip-config";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-IpConfig {
        tlv:id 3;
        description "TLV [15.3]: RpdGlobal.IpConfig";

        leaf IpStackControl {
            tlv:id 1;
            tlv:repr uint8;
            type enumeration {
                enum DualStack  { value  0; description ""; }
                enum IPv4Only   { value  1; description ""; }
                enum IPv6Only   { value  2; description ""; }
            }
            description "TLV [15.3.1]: RpdGlobal.IpConfig.IpStackControl";
        }

    }  // g-IpConfig grouping

}
