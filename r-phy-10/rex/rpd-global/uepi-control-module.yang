module uepi-control-module {
    yang-version 1;
    /* This file is automatically generated with Falcon V System's script.
       Any change made to this file will be lost. */

    namespace "falconvsystems:r-phy-10:uepi-control-module";
    prefix "p-uepi-control";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-UepiControl {
        tlv:id 4;
        description "TLV [15.4]: RpdGlobal.UepiControl";

        leaf ScQamUseRngPw {
            tlv:id 1;
            type boolean;
            description "TLV [15.4.1]: RpdGlobal.UepiControl.ScQamUseRngPw";
        }

        leaf OfdmaMaxNumPayloadUnits {
            tlv:id 2;
            type uint8;
            description "TLV [15.4.2]: RpdGlobal.UepiControl.OfdmaMaxNumPayloadUnits";
        }

        leaf OfdmaMaxNumTrailerUnits {
            tlv:id 3;
            type uint8;
            description "TLV [15.4.3]: RpdGlobal.UepiControl.OfdmaMaxNumTrailerUnits";
        }

    }  // g-UepiControl grouping

}
