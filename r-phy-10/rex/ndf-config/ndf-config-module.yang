module ndf-config-module {
    yang-version 1;
    /* This file is automatically generated with Falcon V System's script.
       Any change made to this file will be lost. */

    namespace "falconvsystems:r-phy-10:ndf-config-module";
    prefix "p-ndf-config";

    // --- imports ---------------------------------------

    import ietf-yang-types {
        prefix "yang";
        /*  External YANG module. */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-NdfConfig {
        tlv:id 94;
        description "TLV [94]: NdfConfig";

        leaf Index {
            // no tlv:id given
            type uint16;
            description
                "TLV [94.X]: NdfConfig.Index
                 non-defaults: [is_key: True]";
        }

        leaf AdminState {
            tlv:id 1;
            tlv:repr uint8;
            type enumeration {
                enum other      { value  1; description ""; }
                enum up         { value  2; description ""; }
                enum down       { value  3; description ""; }
                enum testing    { value  4; description ""; }
            }
            description "TLV [94.1]: NdfConfig.AdminState";
        }

        leaf CcapCoreOwner {
            tlv:id 2;
            type yang:mac-address;
            description "TLV [94.2]: NdfConfig.CcapCoreOwner";
        }

        leaf RfMute {
            tlv:id 3;
            type boolean;
            description "TLV [94.3]: NdfConfig.RfMute";
        }

        leaf CenterFrequency {
            tlv:id 4;
            type uint32;
            units "Hz";
            description "TLV [94.4]: NdfConfig.CenterFrequency";
        }

        leaf ChannelWidth {
            tlv:id 5;
            type uint32;
            units "Hz";
            description "TLV [94.5]: NdfConfig.ChannelWidth";
        }

        leaf PowerAdjust {
            tlv:id 6;
            type int16;
            units "TenthdB";
            description "TLV [94.6]: NdfConfig.PowerAdjust";
        }

    }  // g-NdfConfig grouping

}
