module rpd-connection-status-module {
    yang-version 1;
    /* This file is automatically generated with Falcon V System's script.
       Any change made to this file will be lost. */

    namespace "falconvsystems:r-phy-10:rpd-connection-status-module";
    prefix "p-rpd-connection-status";

    // --- imports ---------------------------------------

    import ietf-yang-types {
        prefix "yang";
        /*  External YANG module. */
    }

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-RpdConnectionStatus {
        tlv:id 105;
        description "TLV [105]: RpdConnectionStatus";

        leaf Index {
            tlv:id 1;
            type uint8;
            description
                "TLV [105.1]: RpdConnectionStatus.Index
                 non-defaults: [is_key: True]";
        }

        leaf CoreId {
            tlv:id 2;
            type yang:mac-address;
            description
                "TLV [105.2]: RpdConnectionStatus.CoreId
                 non-defaults: [is_rcp_readonly: True, is_readonly: True]";
        }

        leaf RpdGcpConnectionStatus {
            tlv:id 3;
            tlv:repr uint8;
            type enumeration {
                enum Inactive       { value  1; description ""; }
                enum Connecting     { value  2; description ""; }
                enum Connected      { value  3; description ""; }
                enum ReConnecting   { value  4; description ""; }
            }
            description
                "TLV [105.3]: RpdConnectionStatus.RpdGcpConnectionStatus
                 non-defaults: [is_rcp_readonly: True, is_readonly: True]";
        }

        leaf AuthenticationStatus {
            tlv:id 4;
            tlv:repr uint8;
            type enumeration {
                enum other              { value  0; description ""; }
                enum authenticated      { value  1; description ""; }
                enum authFailed         { value  2; description ""; }
                enum authNotPerformed   { value  3; description ""; }
            }
            description
                "TLV [105.4]: RpdConnectionStatus.AuthenticationStatus
                 non-defaults: [is_rcp_readonly: True, is_readonly: True]";
        }

    }  // g-RpdConnectionStatus grouping

}
