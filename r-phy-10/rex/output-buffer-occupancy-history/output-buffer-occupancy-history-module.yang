module output-buffer-occupancy-history-module {
    yang-version 1;
    /* This file is automatically generated with Falcon V System's script.
       Any change made to this file will be lost. */

    namespace "falconvsystems:r-phy-10:output-buffer-occupancy-history-module";
    prefix "p-output-buffer-occupancy-history";

    // --- imports ---------------------------------------

    import tlv-extension {
        prefix "tlv";
        /*  Falcon's Yang extension for TLV attributes. */
    }

    // --- meta ------------------------------------------

    organization
        "Falcon V Systems S.A.";

    contact
        "Postal: Falcon V Systems S.A.
         Krzemowa 6, 81-577 Gdynia, POLAND";

    description
        "Automatically translated yang data model definition of RCP (R-PHY Control Protocol)";

    revision 2020-07-02 {
        description
            "Second revision. Files tree is already shaped. Seems there may be still some work needed.";
        reference
            "https://specification-search.cablelabs.com/CM-SP-R-PHY
             https://specification-search.cablelabs.com/CM-SP-R-OSSI";
    }

    // --- definitions -----------------------------------

    grouping g-OutputBufferOccupancyHistory {
        tlv:id 83;
        description "TLV [83]: OutputBufferOccupancyHistory";

        leaf MaximumBufferDepth {
            tlv:id 1;
            type uint32;
            units "bytes";
            description
                "TLV [83.1]: OutputBufferOccupancyHistory.MaximumBufferDepth
                 non-defaults: [is_rcp_readonly: True, is_readonly: True]";
        }

        leaf BufferDepth {
            tlv:id 2;
            type uint32;
            units "bytes";
            description "TLV [83.2]: OutputBufferOccupancyHistory.BufferDepth";
        }

        leaf EnableMonitor {
            tlv:id 3;
            type boolean;
            description "TLV [83.3]: OutputBufferOccupancyHistory.EnableMonitor";
        }

        leaf NormalizationFactor {
            tlv:id 4;
            type uint32;
            description "TLV [83.4]: OutputBufferOccupancyHistory.NormalizationFactor";
        }

        leaf FirstSampleTimestamp {
            tlv:id 5;
            type uint32;
            description
                "TLV [83.5]: OutputBufferOccupancyHistory.FirstSampleTimestamp";
        }

        leaf SampledBufferOccupancy {
            tlv:id 6;
            type binary;
            description
                "TLV [83.6]: OutputBufferOccupancyHistory.SampledBufferOccupancy
                 non-defaults: [is_rcp_readonly: True, is_readonly: True]";
        }

    }  // g-OutputBufferOccupancyHistory grouping

}
