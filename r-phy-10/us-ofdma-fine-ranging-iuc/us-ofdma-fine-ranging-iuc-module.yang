module us-ofdma-fine-ranging-iuc-module {
    yang-version 1;
    /* This file is automatically generated with Falcon V System's script.
       Any change made to this file will be lost. */

    namespace "falconvsystems:r-phy-10:us-ofdma-fine-ranging-iuc-module";
    prefix "p-us-ofdma-fine-ranging-iuc";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-UsOfdmaFineRangingIuc {
        tlv:id 68;
        description "TLV [68]: UsOfdmaFineRangingIuc";
        leaf NumSubcarriers {
            tlv:id 1;
            type uint16;
            description
                "TLV [68.1]: UsOfdmaFineRangingIuc.NumSubcarriers
                 non-defaults: [is_rcp_readonly: True]";
        }

        leaf Guardband {
            tlv:id 2;
            type uint16;
            description
                "TLV [68.2]: UsOfdmaFineRangingIuc.Guardband
                 non-defaults: [is_rcp_readonly: True]";
        }

    }  // g-UsOfdmaFineRangingIuc grouping

}
