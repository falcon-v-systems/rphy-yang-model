module output-buffer-threshold-alert-module {
    yang-version 1;
    /* This file is automatically generated with Falcon V System's script.
       Any change made to this file will be lost. */

    namespace "falconvsystems:r-phy-10:output-buffer-threshold-alert-module";
    prefix "p-output-buffer-threshold-alert";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-OutputBufferThresholdAlert {
        tlv:id 84;
        description "TLV [84]: OutputBufferThresholdAlert";
        leaf BufferDepthMonAlertEnable {
            tlv:id 1;
            type boolean;
            description
                "TLV [84.1]: OutputBufferThresholdAlert.BufferDepthMonAlertEnable";
        }

        leaf BufferDepthMonAlertStatus {
            tlv:id 2;
            tlv:repr uint8;
            type enumeration {
                enum other                { value  1; description ""; }
                enum idle                 { value  2; description ""; }
                enum running              { value  3; description ""; }
                enum thresholdExceeded    { value  4; description ""; }
            }
            description
                "TLV [84.2]: OutputBufferThresholdAlert.BufferDepthMonAlertStatus
                 non-defaults: [is_rcp_readonly: True, is_readonly: True]";
        }

        leaf AlertThreshold {
            tlv:id 3;
            type uint8;
            description "TLV [84.3]: OutputBufferThresholdAlert.AlertThreshold";
        }

        leaf SmoothingFactorN {
            tlv:id 4;
            type uint16;
            description "TLV [84.4]: OutputBufferThresholdAlert.SmoothingFactorN";
        }

        leaf LastAlertTimestamp {
            tlv:id 5;
            type uint32;
            description
                "TLV [84.5]: OutputBufferThresholdAlert.LastAlertTimestamp
                 non-defaults: [is_rcp_readonly: True, is_readonly: True]";
        }

    }  // g-OutputBufferThresholdAlert grouping

}
