module us-ofdma-config-response-module {
    yang-version 1;
    /* This file is automatically generated with Falcon V System's script.
       Any change made to this file will be lost. */

    namespace "falconvsystems:r-phy-10:us-ofdma-config-response-module";
    prefix "p-us-ofdma-config-response";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-UsOfdmaConfigResponse {
        tlv:id 153;
        description
            "TLV [153]: UsOfdmaConfigResponse
             non-defaults: [is_rcp_readonly: True]";
        leaf ResponseOfdmaRollOffPeriod {
            tlv:id 1;
            tlv:repr uint8;
            type enumeration {
                enum 0    { value  1; description ""; }
                enum 32   { value  2; description ""; }
                enum 64   { value  3; description ""; }
                enum 96   { value  4; description ""; }
                enum 128  { value  5; description ""; }
                enum 160  { value  6; description ""; }
                enum 192  { value  7; description ""; }
                enum 224  { value  8; description ""; }
            }
            description
                "TLV [153.1]: UsOfdmaConfigResponse.ResponseOfdmaRollOffPeriod
                 non-defaults: [is_rcp_readonly: True]";
        }

        leaf ResponseOfdmaCyclicPrefix {
            tlv:id 2;
            tlv:repr uint16;
            type enumeration {
                enum 96   { value  1; description ""; }
                enum 128  { value  2; description ""; }
                enum 160  { value  3; description ""; }
                enum 192  { value  4; description ""; }
                enum 224  { value  5; description ""; }
                enum 256  { value  6; description ""; }
                enum 288  { value  7; description ""; }
                enum 320  { value  8; description ""; }
                enum 384  { value  9; description ""; }
                enum 512  { value 10; description ""; }
                enum 640  { value 11; description ""; }
            }
            description
                "TLV [153.2]: UsOfdmaConfigResponse.ResponseOfdmaCyclicPrefix
                 non-defaults: [is_rcp_readonly: True]";
        }

        leaf ResponseOfdmaPreambleString {
            tlv:id 3;
            type binary;
            description
                "TLV [153.3]: UsOfdmaConfigResponse.ResponseOfdmaPreambleString
                 non-defaults: [is_rcp_readonly: True]";
        }

        leaf ResponseNumSymbolsPerFrame {
            tlv:id 4;
            type uint8;
            description
                "TLV [153.4]: UsOfdmaConfigResponse.ResponseNumSymbolsPerFrame
                 non-defaults: [is_rcp_readonly: True]";
        }

        leaf ResponseOfdmaScramblerSeed {
            tlv:id 5;
            type uint32;
            description
                "TLV [153.5]: UsOfdmaConfigResponse.ResponseOfdmaScramblerSeed
                 non-defaults: [is_rcp_readonly: True]";
        }

    }  // g-UsOfdmaConfigResponse grouping

}
