module ndr-config-module {
    yang-version 1;
    /* This file is automatically generated with Falcon V System's script.
       Any change made to this file will be lost. */

    namespace "falconvsystems:r-phy-10:ndr-config-module";
    prefix "p-ndr-config";

    // --- imports ---------------------------------------

    import ietf-yang-types {
        prefix "yang";
        description 
            "External YANG module.";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-NdrConfig {
        tlv:id 95;
        description "TLV [95]: NdrConfig";
        leaf Index {
            // no tlv:id given
            type uint16;
            description
                "TLV [95.X]: NdrConfig.Index
                 non-defaults: [is_key: True]";
        }

        leaf AdminState {
            tlv:id 1;
            tlv:repr uint8;
            type enumeration {
                enum other    { value  1; description ""; }
                enum up       { value  2; description ""; }
                enum down     { value  3; description ""; }
                enum testing  { value  4; description ""; }
            }
            description "TLV [95.1]: NdrConfig.AdminState";
        }

        leaf CcapCoreOwner {
            tlv:id 2;
            type yang:mac-address;
            description "TLV [95.2]: NdrConfig.CcapCoreOwner";
        }

        leaf CenterFrequency {
            tlv:id 3;
            type uint32;
            units "Hz";
            description "TLV [95.3]: NdrConfig.CenterFrequency";
        }

        leaf ChannelWidth {
            tlv:id 4;
            type uint32;
            units "Hz";
            description "TLV [95.4]: NdrConfig.ChannelWidth";
        }

        leaf TargetRxPowerAdjust {
            tlv:id 5;
            type int16;
            units "TenthdBmV";
            description "TLV [95.5]: NdrConfig.TargetRxPowerAdjust";
        }

    }  // g-NdrConfig grouping

}
