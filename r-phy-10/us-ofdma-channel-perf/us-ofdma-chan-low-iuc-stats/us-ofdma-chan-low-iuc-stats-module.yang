module us-ofdma-chan-low-iuc-stats-module {
    yang-version 1;
    /* This file is automatically generated with Falcon V System's script.
       Any change made to this file will be lost. */

    namespace "falconvsystems:r-phy-10:us-ofdma-chan-low-iuc-stats-module";
    prefix "p-us-ofdma-chan-low-iuc-stats";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-UsOfdmaChanLowIucStats {
        tlv:id 1;
        description "TLV [79.1]: UsOfdmaChannelPerf.UsOfdmaChanLowIucStats";
        leaf UsIuc {
            tlv:id 1;
            tlv:repr uint8;
            type enumeration {
                enum 1    { value  1; description ""; }
                enum 2    { value  2; description ""; }
                enum 3    { value  3; description ""; }
            }
            description
                "TLV [79.1.1]: UsOfdmaChannelPerf.UsOfdmaChanLowIucStats.UsIuc";
        }

        leaf UnicastOpportunities {
            tlv:id 2;
            type uint64;
            description
                "TLV [79.1.2]: UsOfdmaChannelPerf.UsOfdmaChanLowIucStats.UnicastOpportunities
                 non-defaults: [is_rcp_readonly: True, is_readonly: True]";
        }

        leaf UnicastOpCollisions {
            tlv:id 3;
            type uint64;
            description
                "TLV [79.1.3]: UsOfdmaChannelPerf.UsOfdmaChanLowIucStats.UnicastOpCollisions
                 non-defaults: [is_rcp_readonly: True, is_readonly: True]";
        }

        leaf UnicastOpNoEnergy {
            tlv:id 4;
            type uint64;
            description
                "TLV [79.1.4]: UsOfdmaChannelPerf.UsOfdmaChanLowIucStats.UnicastOpNoEnergy
                 non-defaults: [is_rcp_readonly: True, is_readonly: True]";
        }

        leaf UnicastOpErrors {
            tlv:id 5;
            type uint64;
            description
                "TLV [79.1.5]: UsOfdmaChannelPerf.UsOfdmaChanLowIucStats.UnicastOpErrors
                 non-defaults: [is_rcp_readonly: True, is_readonly: True]";
        }

        leaf MulticastOpportunities {
            tlv:id 6;
            type uint64;
            description
                "TLV [79.1.6]: UsOfdmaChannelPerf.UsOfdmaChanLowIucStats.MulticastOpportunities
                 non-defaults: [is_rcp_readonly: True, is_readonly: True]";
        }

        leaf McastOpCollisions {
            tlv:id 7;
            type uint64;
            description
                "TLV [79.1.7]: UsOfdmaChannelPerf.UsOfdmaChanLowIucStats.McastOpCollisions
                 non-defaults: [is_rcp_readonly: True, is_readonly: True]";
        }

        leaf McastOpNoEnergy {
            tlv:id 8;
            type uint64;
            description
                "TLV [79.1.8]: UsOfdmaChannelPerf.UsOfdmaChanLowIucStats.McastOpNoEnergy
                 non-defaults: [is_rcp_readonly: True, is_readonly: True]";
        }

        leaf McastOpErrors {
            tlv:id 9;
            type uint64;
            description
                "TLV [79.1.9]: UsOfdmaChannelPerf.UsOfdmaChanLowIucStats.McastOpErrors
                 non-defaults: [is_rcp_readonly: True, is_readonly: True]";
        }

        leaf NumPredecodePass {
            tlv:id 10;
            type uint64;
            description
                "TLV [79.1.10]: UsOfdmaChannelPerf.UsOfdmaChanLowIucStats.NumPredecodePass
                 non-defaults: [is_rcp_readonly: True, is_readonly: True]";
        }

        leaf NumPostdecodePass {
            tlv:id 11;
            type uint64;
            description
                "TLV [79.1.11]: UsOfdmaChannelPerf.UsOfdmaChanLowIucStats.NumPostdecodePass
                 non-defaults: [is_rcp_readonly: True, is_readonly: True]";
        }

        leaf NumPostdecodeFail {
            tlv:id 12;
            type uint64;
            description
                "TLV [79.1.12]: UsOfdmaChannelPerf.UsOfdmaChanLowIucStats.NumPostdecodeFail
                 non-defaults: [is_rcp_readonly: True, is_readonly: True]";
        }

    }  // g-UsOfdmaChanLowIucStats grouping

}
