module us-ofdma-channel-perf-module {
    yang-version 1;
    /* This file is automatically generated with Falcon V System's script.
       Any change made to this file will be lost. */

    namespace "falconvsystems:r-phy-10:us-ofdma-channel-perf-module";
    prefix "p-us-ofdma-channel-perf";

    // --- imports ---------------------------------------

    import tlv-ext {
        prefix "tlv";
        description 
            "Falcon's Yang extension for TLV attributes.";
    }

    import ucd-refresh-status-ofdma-module {
        prefix "p-ucd-refresh-status-ofdma";
        description 
            "File path: us-ofdma-channel-perf/ucd-refresh-status-ofdma/ucd-refresh-status-ofdma-module.yang
            https://github.com/falcon-v-systems/rphy-yang-model/blob/master/r-phy-10/us-ofdma-channel-perf/ucd-refresh-status-ofdma/ucd-refresh-status-ofdma-module.yang";
    }

    import us-ofdma-chan-low-iuc-stats-module {
        prefix "p-us-ofdma-chan-low-iuc-stats";
        description 
            "File path: us-ofdma-channel-perf/us-ofdma-chan-low-iuc-stats/us-ofdma-chan-low-iuc-stats-module.yang
            https://github.com/falcon-v-systems/rphy-yang-model/blob/master/r-phy-10/us-ofdma-channel-perf/us-ofdma-chan-low-iuc-stats/us-ofdma-chan-low-iuc-stats-module.yang";
    }

    import us-ofdma-hi-iuc-stats-module {
        prefix "p-us-ofdma-hi-iuc-stats";
        description 
            "File path: us-ofdma-channel-perf/us-ofdma-hi-iuc-stats/us-ofdma-hi-iuc-stats-module.yang
            https://github.com/falcon-v-systems/rphy-yang-model/blob/master/r-phy-10/us-ofdma-channel-perf/us-ofdma-hi-iuc-stats/us-ofdma-hi-iuc-stats-module.yang";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-UsOfdmaChannelPerf {
        tlv:id 79;
        description "TLV [79]: UsOfdmaChannelPerf";
        leaf Index {
            // no tlv:id given
            type uint16;
            description
                "TLV [79.X]: UsOfdmaChannelPerf.Index
                 non-defaults: [is_key: True]";
        }

        container UsOfdmaChanLowIucStats {
            tlv:id 1;
            description "TLV [79.1]: UsOfdmaChannelPerf.UsOfdmaChanLowIucStats";
            uses "p-us-ofdma-chan-low-iuc-stats:g-UsOfdmaChanLowIucStats";
        }

        container UsOfdmaHiIucStats {
            tlv:id 2;
            description "TLV [79.2]: UsOfdmaChannelPerf.UsOfdmaHiIucStats";
            uses "p-us-ofdma-hi-iuc-stats:g-UsOfdmaHiIucStats";
        }

        leaf HcsErrors {
            tlv:id 3;
            type uint64;
            description
                "TLV [79.3]: UsOfdmaChannelPerf.HcsErrors
                 non-defaults: [is_rcp_readonly: True, is_readonly: True]";
        }

        leaf LateMaps {
            tlv:id 4;
            type uint64;
            description
                "TLV [79.4]: UsOfdmaChannelPerf.LateMaps
                 non-defaults: [is_rcp_readonly: True, is_readonly: True]";
        }

        leaf IllegalMaps {
            tlv:id 5;
            type uint64;
            description
                "TLV [79.5]: UsOfdmaChannelPerf.IllegalMaps
                 non-defaults: [is_rcp_readonly: True, is_readonly: True]";
        }

        leaf DiscardedRequests {
            tlv:id 6;
            type uint64;
            description
                "TLV [79.6]: UsOfdmaChannelPerf.DiscardedRequests
                 non-defaults: [is_rcp_readonly: True, is_readonly: True]";
        }

        leaf ProbeGrants {
            tlv:id 7;
            type uint64;
            description
                "TLV [79.7]: UsOfdmaChannelPerf.ProbeGrants
                 non-defaults: [is_rcp_readonly: True, is_readonly: True]";
        }

        leaf discontinuityTime {
            tlv:id 8;
            type binary;
            description
                "TLV [79.8]: UsOfdmaChannelPerf.discontinuityTime
                 non-defaults: [is_rcp_readonly: True, is_readonly: True]";
        }

        leaf operStatusUsScQam {
            tlv:id 9;
            tlv:repr uint8;
            type enumeration {
                enum up       { value  1; description ""; }
                enum down     { value  2; description ""; }
            }
            description
                "TLV [79.9]: UsOfdmaChannelPerf.operStatusUsScQam
                 non-defaults: [is_rcp_readonly: True, is_readonly: True]";
        }

        container UcdRefreshStatusOfdma {
            tlv:id 10;
            description
                "TLV [79.10]: UsOfdmaChannelPerf.UcdRefreshStatusOfdma
                 non-defaults: [is_rcp_readonly: True, is_readonly: True]";
            uses "p-ucd-refresh-status-ofdma:g-UcdRefreshStatusOfdma";
        }

    }  // g-UsOfdmaChannelPerf grouping

}
