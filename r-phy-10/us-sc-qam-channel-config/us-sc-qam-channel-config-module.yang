module us-sc-qam-channel-config-module {
    yang-version 1;
    /* This file is automatically generated with Falcon V System's script.
       Any change made to this file will be lost. */

    namespace "falconvsystems:r-phy-10:us-sc-qam-channel-config-module";
    prefix "p-us-sc-qam-channel-config";

    // --- imports ---------------------------------------

    import ietf-yang-types {
        prefix "yang";
        description 
            "External YANG module.";
    }

    import interval-usage-code-module {
        prefix "p-interval-usage-code";
        description 
            "File path: us-sc-qam-channel-config/interval-usage-code/interval-usage-code-module.yang
            https://github.com/falcon-v-systems/rphy-yang-model/blob/master/r-phy-10/us-sc-qam-channel-config/interval-usage-code/interval-usage-code-module.yang";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-UsScQamChannelConfig {
        tlv:id 65;
        description "TLV [65]: UsScQamChannelConfig";
        leaf Index {
            // no tlv:id given
            type uint16;
            description
                "TLV [65.X]: UsScQamChannelConfig.Index
                 non-defaults: [is_key: True]";
        }

        leaf ModulationProfileIndex {
            // no tlv:id given
            type uint32;
            description "TLV [65.X]: UsScQamChannelConfig.ModulationProfileIndex";
        }

        leaf AdminState {
            tlv:id 1;
            tlv:repr uint8;
            type enumeration {
                enum other    { value  1; description ""; }
                enum up       { value  2; description ""; }
                enum down     { value  3; description ""; }
                enum testing  { value  4; description ""; }
            }
            description "TLV [65.1]: UsScQamChannelConfig.AdminState";
        }

        leaf CcapCoreOwner {
            tlv:id 2;
            type yang:mac-address;
            description "TLV [65.2]: UsScQamChannelConfig.CcapCoreOwner";
        }

        leaf ChannelType {
            tlv:id 3;
            tlv:repr uint8;
            type enumeration {
                enum Unknown          { value  0; description ""; }
                enum TDMA             { value  1; description ""; }
                enum ATDMA            { value  2; description ""; }
                enum Reserved         { value  3; description ""; }
                enum TDMAandATDMA     { value  4; description ""; }
            }
            description
                "TLV [65.3]: UsScQamChannelConfig.ChannelType
                 non-defaults: [is_rcp_readonly: True]";
        }

        leaf CenterFrequency {
            tlv:id 4;
            type uint32;
            units "Hz";
            description
                "TLV [65.4]: UsScQamChannelConfig.CenterFrequency
                 non-defaults: [is_rcp_readonly: True]";
        }

        leaf Width {
            tlv:id 5;
            tlv:repr uint32;
            type enumeration {
                enum 200000   { value 200000; description ""; }
                enum 400000   { value 400000; description ""; }
                enum 800000   { value 800000; description ""; }
                enum 1600000  { value 1600000; description ""; }
                enum 3200000  { value 3200000; description ""; }
                enum 6400000  { value 6400000; description ""; }
            }
            units "Hz";
            description
                "TLV [65.5]: UsScQamChannelConfig.Width
                 non-defaults: [is_rcp_readonly: True]";
        }

        leaf SlotSize {
            tlv:id 6;
            tlv:repr uint32;
            type enumeration {
                enum 1    { value  1; description ""; }
                enum 2    { value  2; description ""; }
                enum 4    { value  4; description ""; }
                enum 8    { value  8; description ""; }
                enum 16   { value 16; description ""; }
                enum 32   { value 32; description ""; }
                enum 64   { value 64; description ""; }
                enum 128  { value 128; description ""; }
            }
            description
                "TLV [65.6]: UsScQamChannelConfig.SlotSize
                 non-defaults: [is_rcp_readonly: True]";
        }

        leaf StartingMinislot {
            tlv:id 7;
            type uint32;
            description
                "TLV [65.7]: UsScQamChannelConfig.StartingMinislot
                 non-defaults: [is_rcp_readonly: True]";
        }

        leaf PreambleString {
            tlv:id 8;
            type binary;
            description
                "TLV [65.8]: UsScQamChannelConfig.PreambleString
                 non-defaults: [is_rcp_readonly: True]";
        }

        leaf TargetRxPowerAdjust {
            tlv:id 9;
            type int16;
            units "TenthdBmV";
            description "TLV [65.9]: UsScQamChannelConfig.TargetRxPowerAdjust";
        }

        list IntervalUsageCode {
            tlv:id 10;
            key Code;
            description "TLV [65.10]: UsScQamChannelConfig.IntervalUsageCode";
            uses "p-interval-usage-code:g-IntervalUsageCode";
        }

        leaf EqualizationCoeffEnable {
            tlv:id 11;
            type boolean;
            description "TLV [65.11]: UsScQamChannelConfig.EqualizationCoeffEnable";
        }

        leaf IngressNoiseCancelEnable {
            tlv:id 12;
            type boolean;
            description "TLV [65.12]: UsScQamChannelConfig.IngressNoiseCancelEnable";
        }

        leaf UsChanId {
            tlv:id 13;
            type uint8;
            description
                "TLV [65.13]: UsScQamChannelConfig.UsChanId
                 non-defaults: [is_rcp_readonly: True, is_readonly: True]";
        }

        leaf ConfigChangeCount {
            tlv:id 14;
            type uint8;
            description
                "TLV [65.14]: UsScQamChannelConfig.ConfigChangeCount
                 non-defaults: [is_rcp_readonly: True, is_readonly: True]";
        }

        leaf DsChanId {
            tlv:id 15;
            type uint8;
            description
                "TLV [65.15]: UsScQamChannelConfig.DsChanId
                 non-defaults: [is_rcp_readonly: True, is_readonly: True]";
        }

    }  // g-UsScQamChannelConfig grouping

}
