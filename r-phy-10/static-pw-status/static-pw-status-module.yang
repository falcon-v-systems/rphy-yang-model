module static-pw-status-module {
    yang-version 1;
    /* This file is automatically generated with Falcon V System's script.
       Any change made to this file will be lost. */

    namespace "falconvsystems:r-phy-10:static-pw-status-module";
    prefix "p-static-pw-status";

    // --- imports ---------------------------------------

    import common-static-pw-status-module {
        prefix "p-common-static-pw-status";
        description 
            "File path: static-pw-status/common-static-pw-status/common-static-pw-status-module.yang
            https://github.com/falcon-v-systems/rphy-yang-model/blob/master/r-phy-10/static-pw-status/common-static-pw-status/common-static-pw-status-module.yang";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-StaticPwStatus {
        tlv:id 59;
        description "TLV [59]: StaticPwStatus";
        container CommonStaticPwStatus {
            tlv:id 1;
            description "TLV [59.1]: StaticPwStatus.CommonStaticPwStatus";
            uses "p-common-static-pw-status:g-CommonStaticPwStatus";
        }

    }  // g-StaticPwStatus grouping

}
