module sid-qos-module {
    yang-version 1;
    /* This file is automatically generated with Falcon V System's script.
       Any change made to this file will be lost. */

    namespace "falconvsystems:r-phy-10:sid-qos-module";
    prefix "p-sid-qos";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-SidQos {
        tlv:id 96;
        description "TLV [96]: SidQos";
        leaf StartSid {
            tlv:id 1;
            type uint16;
            description
                "TLV [96.1]: SidQos.StartSid
                 non-defaults: [is_key: True]";
        }

        leaf NumSids {
            tlv:id 2;
            type uint16;
            description "TLV [96.2]: SidQos.NumSids";
        }

        leaf SidSfType {
            tlv:id 3;
            tlv:repr uint8;
            type enumeration {
                enum SID                  { value  0; description ""; }
                enum Other                { value  1; description ""; }
                enum LegacyScQamCh        { value  2; description ""; }
                enum SegmentHeaderOn      { value  3; description ""; }
                enum SegmentHeaderOff     { value  4; description ""; }
            }
            description "TLV [96.3]: SidQos.SidSfType";
        }

        leaf SidUepiFlowId {
            tlv:id 4;
            type uint8;
            description "TLV [96.4]: SidQos.SidUepiFlowId";
        }

        leaf SidFlowTag {
            tlv:id 5;
            type uint32;
            description "TLV [96.5]: SidQos.SidFlowTag";
        }

    }  // g-SidQos grouping

}
