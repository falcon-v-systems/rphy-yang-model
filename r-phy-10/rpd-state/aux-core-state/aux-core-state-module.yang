module aux-core-state-module {
    yang-version 1;
    /* This file is automatically generated with Falcon V System's script.
       Any change made to this file will be lost. */

    namespace "falconvsystems:r-phy-10:aux-core-state-module";
    prefix "p-aux-core-state";

    // --- imports ---------------------------------------

    import ietf-inet-types {
        prefix "inet";
        description 
            "External YANG module.";
    }

    import ietf-yang-types {
        prefix "yang";
        description 
            "External YANG module.";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-AuxCoreState {
        tlv:id 4;
        description "TLV [87.4]: RpdState.AuxCoreState";
        leaf AuxCoreIndex {
            tlv:id 1;
            type uint8;
            description
                "TLV [87.4.1]: RpdState.AuxCoreState.AuxCoreIndex
                 non-defaults: [is_key: True]";
        }

        leaf AuxCoreId {
            tlv:id 2;
            type yang:mac-address;
            description
                "TLV [87.4.2]: RpdState.AuxCoreState.AuxCoreId
                 non-defaults: [is_rcp_readonly: True, is_readonly: True]";
        }

        leaf AuxCoreIp {
            tlv:id 3;
            type inet:ip-address;
            description
                "TLV [87.4.3]: RpdState.AuxCoreState.AuxCoreIp
                 non-defaults: [is_key: True, is_rcp_readonly: True, is_readonly: True]";
        }

        leaf AuxCoreRPDState {
            tlv:id 4;
            tlv:repr uint8;
            type enumeration {
                enum AuthenticatetoCore       { value  1; description ""; }
                enum GcpConfigAuxCore         { value  2; description ""; }
                enum WaitForRcpIraReq         { value  3; description ""; }
                enum WaitForConfigRexReq      { value  4; description ""; }
                enum WaitOperationalAuxCore   { value  5; description ""; }
                enum OperationalAuxCore       { value  6; description ""; }
            }
            description
                "TLV [87.4.4]: RpdState.AuxCoreState.AuxCoreRPDState
                 non-defaults: [is_rcp_readonly: True, is_readonly: True]";
        }

    }  // g-AuxCoreState grouping

}
