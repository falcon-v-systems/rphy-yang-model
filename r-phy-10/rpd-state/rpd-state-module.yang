module rpd-state-module {
    yang-version 1;
    /* This file is automatically generated with Falcon V System's script.
       Any change made to this file will be lost. */

    namespace "falconvsystems:r-phy-10:rpd-state-module";
    prefix "p-rpd-state";

    // --- imports ---------------------------------------

    import aux-core-state-module {
        prefix "p-aux-core-state";
        description 
            "File path: rpd-state/aux-core-state/aux-core-state-module.yang
            https://github.com/falcon-v-systems/rphy-yang-model/blob/master/r-phy-10/rpd-state/aux-core-state/aux-core-state-module.yang";
    }

    import network-authentication-state-module {
        prefix "p-network-authentication-state";
        description 
            "File path: rpd-state/network-authentication-state/network-authentication-state-module.yang
            https://github.com/falcon-v-systems/rphy-yang-model/blob/master/r-phy-10/rpd-state/network-authentication-state/network-authentication-state-module.yang";
    }

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-RpdState {
        tlv:id 87;
        description
            "TLV [87]: RpdState
             non-defaults: [is_rcp_readonly: True, is_readonly: True]";
        leaf TopLevelRPDState {
            tlv:id 1;
            tlv:repr uint8;
            type enumeration {
                enum LocalRPDInit                     { value  1; description ""; }
                enum NetworkAuthentication            { value  2; description ""; }
                enum IPAddressAssignment              { value  3; description ""; }
                enum WaitingTOD                       { value  4; description ""; }
                enum ConnectPrincipalCore             { value  5; description ""; }
                enum WaitOperationalPrincipalCore     { value  6; description ""; }
                enum OperationalPrincipalCore         { value  7; description ""; }
            }
            description
                "TLV [87.1]: RpdState.TopLevelRPDState
                 non-defaults: [is_rcp_readonly: True, is_readonly: True]";
        }

        list NetworkAuthenticationState {
            tlv:id 2;
            key NetworkAuthenticationPortIndex;
            description
                "TLV [87.2]: RpdState.NetworkAuthenticationState
                 non-defaults: [is_rcp_readonly: True, is_readonly: True]";
            uses "p-network-authentication-state:g-NetworkAuthenticationState";
        }

        leaf ConnectPrincipalCoreSubState {
            tlv:id 3;
            tlv:repr uint8;
            type enumeration {
                enum AuthenticatetoCore       { value  1; description ""; }
                enum GcpConfigPrincipalCore   { value  2; description ""; }
                enum WaitForRcpIraReq         { value  3; description ""; }
                enum WaitLConfigRexReq        { value  4; description ""; }
            }
            description
                "TLV [87.3]: RpdState.ConnectPrincipalCoreSubState
                 non-defaults: [is_rcp_readonly: True, is_readonly: True]";
        }

        list AuxCoreState {
            tlv:id 4;
            key AuxCoreIndex AuxCoreIp;
            description "TLV [87.4]: RpdState.AuxCoreState";
            uses "p-aux-core-state:g-AuxCoreState";
        }

        leaf LocalPtpSyncStatus {
            tlv:id 5;
            type boolean;
            description
                "TLV [87.5]: RpdState.LocalPtpSyncStatus
                 non-defaults: [is_rcp_readonly: True, is_readonly: True]";
        }

    }  // g-RpdState grouping

}
