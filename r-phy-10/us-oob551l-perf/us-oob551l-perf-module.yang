module us-oob551l-perf-module {
    yang-version 1;
    /* This file is automatically generated with Falcon V System's script.
       Any change made to this file will be lost. */

    namespace "falconvsystems:r-phy-10:us-oob551l-perf-module";
    prefix "p-us-oob551l-perf";

    // --- imports ---------------------------------------

    import tlv-ext {
        prefix "tlv";
        description 
            "Falcon's Yang extension for TLV attributes.";
    }

    // --- meta ------------------------------------------

    organization
        "Falcon V Systems S.A.";

    contact
        "Postal: Falcon V Systems S.A.
         Krzemowa 6, 81-577 Gdynia, POLAND";

    description
        "PoC focused on YANG adaptation";

    revision 2020-06-13 {
        description
            "Initial revision.";
        reference
            "https://specification-search.cablelabs.com/CM-SP-R-PHY";
    }

    // --- definitions -----------------------------------

    grouping g-UsOob551lPerf {
        tlv:id 80;
        description
            "TLV [80]: UsOob551lPerf
             non-defaults: [is_rcp_readonly: True, is_readonly: True]";
        leaf operStatusUsOob551 {
            tlv:id 1;
            tlv:repr uint8;
            type enumeration {
                enum up       { value  1; description ""; }
                enum down     { value  2; description ""; }
            }
            description
                "TLV [80.1]: UsOob551lPerf.operStatusUsOob551
                 non-defaults: [is_rcp_readonly: True, is_readonly: True]";
        }

    }  // g-UsOob551lPerf grouping

}
